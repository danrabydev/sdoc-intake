[DOCUMENT]
TITLE: NIST SP 800-53 Rev 5
UID: TPL-NIST-800-53
VERSION: 5.2.0
DATE: 2026-05-11
CLASSIFICATION: Unclassified
ROOT: False

[GRAMMAR]
ELEMENTS:
- TAG: TEXT
  FIELDS:
  - TITLE: STATEMENT
    TYPE: String
    REQUIRED: True
- TAG: SECTION
  PROPERTIES:
    IS_COMPOSITE: True
  FIELDS:
  - TITLE: UID
    TYPE: String
    REQUIRED: False
  - TITLE: TITLE
    TYPE: String
    REQUIRED: True
- TAG: REQUIREMENT
  FIELDS:
  - TITLE: UID
    TYPE: String
    REQUIRED: False
  - TITLE: TITLE
    TYPE: String
    REQUIRED: False
  - TITLE: STATEMENT
    TYPE: String
    REQUIRED: False
  - TITLE: COMMENT
    TYPE: String
    REQUIRED: False
  - TITLE: BASELINE
    TYPE: SingleChoice(Low, Moderate, High, Privacy, None)
    REQUIRED: False
  - TITLE: STATUS
    TYPE: SingleChoice(Draft, Active, Approved)
    REQUIRED: False
  RELATIONS:
  - TYPE: Parent
  - TYPE: Child
  - TYPE: File
  - TYPE: Parent
    ROLE: Refines
  - TYPE: Parent
    ROLE: Satisfies
  - TYPE: Parent
    ROLE: Uses
  - TYPE: Parent
    ROLE: ConformsTo

[TEXT]
STATEMENT: >>>
Template for NIST Special Publication 800-53, Revision 5.2.0, Security and Privacy Controls for Information Systems and Organizations, catalog dated 11 May 2026.
20 families. Each requirement is a control or an enhancement. The UID is the control identifier, with an enhancement written as AC-2.1 for AC-2(1).
BASELINE is the lowest SP 800-53B selection that includes the control: Low, Moderate, High, or Privacy. None means it is not in those baselines. Withdrawn controls say so in the comment.
Copy this file into the document root before use. Link a product requirement with Parent role ConformsTo and the control UID.
The statement is the control requirement. Guidance and assessment procedures stay in the official publication.
<<<

[[SECTION]]
UID: NIST-AC
TITLE: AC — Access Control

[REQUIREMENT]
UID: AC-1
TITLE: AC-1 Policy and Procedures
STATEMENT: >>>
a. Develop, document, and disseminate to [organization-defined personnel or roles]:

  1. [ac-01_odp.03] access control policy that:

    (a) Addresses purpose, scope, roles, responsibilities, management commitment, coordination among organizational entities, and compliance; and

    (b) Is consistent with applicable laws, executive orders, directives, regulations, policies, standards, and guidelines; and

  2. Procedures to facilitate the implementation of the access control policy and the associated access controls;

b. Designate an [official] to manage the development, documentation, and dissemination of the access control policy and procedures; and

c. Review and update the current access control:

  1. Policy [frequency] and following [events] ; and

  2. Procedures [frequency] and following [events].
<<<
COMMENT: Baselines: Low, Moderate, High, Privacy
BASELINE: Low
STATUS: Draft

[REQUIREMENT]
UID: AC-2
TITLE: AC-2 Account Management
STATEMENT: >>>
a. Define and document the types of accounts allowed and specifically prohibited for use within the system;

b. Assign account managers;

c. Require [prerequisites and criteria] for group and role membership;

d. Specify:

  1. Authorized users of the system;

  2. Group and role membership; and

  3. Access authorizations (i.e., privileges) and [attributes (as required)] for each account;

e. Require approvals by [personnel or roles] for requests to create accounts;

f. Create, enable, modify, disable, and remove accounts in accordance with [policy, procedures, prerequisites, and criteria];

g. Monitor the use of accounts;

h. Notify account managers and [personnel or roles] within:

  1. [time period] when accounts are no longer required;

  2. [time period] when users are terminated or transferred; and

  3. [time period] when system usage or need-to-know changes for an individual;

i. Authorize access to the system based on:

  1. A valid access authorization;

  2. Intended system usage; and

  3. [attributes (as required)];

j. Review accounts for compliance with account management requirements [frequency];

k. Establish and implement a process for changing shared or group account authenticators (if deployed) when individuals are removed from the group; and

l. Align account management processes with personnel termination and transfer processes.
<<<
COMMENT: Baselines: Low, Moderate, High
BASELINE: Low
STATUS: Draft

[REQUIREMENT]
UID: AC-2.1
TITLE: AC-2(1) Automated System Account Management
STATEMENT: >>>
Support the management of system accounts using [automated mechanisms].
<<<
COMMENT: Baselines: Moderate, High
BASELINE: Moderate
STATUS: Draft

[REQUIREMENT]
UID: AC-2.2
TITLE: AC-2(2) Automated Temporary and Emergency Account Management
STATEMENT: >>>
Automatically [ac-02.02_odp.01] temporary and emergency accounts after [time period].
<<<
COMMENT: Baselines: Moderate, High
BASELINE: Moderate
STATUS: Draft

[REQUIREMENT]
UID: AC-2.3
TITLE: AC-2(3) Disable Accounts
STATEMENT: >>>
Disable accounts within [time period] when the accounts:

  (a) Have expired;

  (b) Are no longer associated with a user or individual;

  (c) Are in violation of organizational policy; or

  (d) Have been inactive for [time period].
<<<
COMMENT: Baselines: Moderate, High
BASELINE: Moderate
STATUS: Draft

[REQUIREMENT]
UID: AC-2.4
TITLE: AC-2(4) Automated Audit Actions
STATEMENT: >>>
Automatically audit account creation, modification, enabling, disabling, and removal actions.
<<<
COMMENT: Baselines: Moderate, High
BASELINE: Moderate
STATUS: Draft

[REQUIREMENT]
UID: AC-2.5
TITLE: AC-2(5) Inactivity Logout
STATEMENT: >>>
Require that users log out when [time period of expected inactivity or description of when to log out].
<<<
COMMENT: Baselines: Moderate, High
BASELINE: Moderate
STATUS: Draft

[REQUIREMENT]
UID: AC-2.6
TITLE: AC-2(6) Dynamic Privilege Management
STATEMENT: >>>
Implement [dynamic privilege management capabilities].
<<<
BASELINE: None
STATUS: Draft

[REQUIREMENT]
UID: AC-2.7
TITLE: AC-2(7) Privileged User Accounts
STATEMENT: >>>
(a) Establish and administer privileged user accounts in accordance with [ac-02.07_odp];

(b) Monitor privileged role or attribute assignments;

(c) Monitor changes to roles or attributes; and

(d) Revoke access when privileged role or attribute assignments are no longer appropriate.
<<<
BASELINE: None
STATUS: Draft

[REQUIREMENT]
UID: AC-2.8
TITLE: AC-2(8) Dynamic Account Management
STATEMENT: >>>
Create, activate, manage, and deactivate [system accounts] dynamically.
<<<
BASELINE: None
STATUS: Draft

[REQUIREMENT]
UID: AC-2.9
TITLE: AC-2(9) Restrictions on Use of Shared and Group Accounts
STATEMENT: >>>
Only permit the use of shared and group accounts that meet [conditions].
<<<
BASELINE: None
STATUS: Draft

[REQUIREMENT]
UID: AC-2.10
TITLE: AC-2(10) Shared and Group Account Credential Change
STATEMENT: >>>
Withdrawn. Incorporated into AC-2_SMT.K.
<<<
COMMENT: Withdrawn
BASELINE: None
STATUS: Draft

[REQUIREMENT]
UID: AC-2.11
TITLE: AC-2(11) Usage Conditions
STATEMENT: >>>
Enforce [circumstances and/or usage conditions] for [system accounts].
<<<
COMMENT: Baselines: High
BASELINE: High
STATUS: Draft

[REQUIREMENT]
UID: AC-2.12
TITLE: AC-2(12) Account Monitoring for Atypical Usage
STATEMENT: >>>
(a) Monitor system accounts for [atypical usage] ; and

(b) Report atypical usage of system accounts to [personnel or roles].
<<<
COMMENT: Baselines: High
BASELINE: High
STATUS: Draft

[REQUIREMENT]
UID: AC-2.13
TITLE: AC-2(13) Disable Accounts for High-risk Individuals
STATEMENT: >>>
Disable accounts of individuals within [time period] of discovery of [significant risks].
<<<
COMMENT: Baselines: Moderate, High
BASELINE: Moderate
STATUS: Draft

[REQUIREMENT]
UID: AC-3
TITLE: AC-3 Access Enforcement
STATEMENT: >>>
Enforce approved authorizations for logical access to information and system resources in accordance with applicable access control policies.
<<<
COMMENT: Baselines: Low, Moderate, High
BASELINE: Low
STATUS: Draft

[REQUIREMENT]
UID: AC-3.1
TITLE: AC-3(1) Restricted Access to Privileged Functions
STATEMENT: >>>
Withdrawn. Incorporated into AC-6.
<<<
COMMENT: Withdrawn
BASELINE: None
STATUS: Draft

[REQUIREMENT]
UID: AC-3.2
TITLE: AC-3(2) Dual Authorization
STATEMENT: >>>
Enforce dual authorization for [privileged commands and/or other actions].
<<<
BASELINE: None
STATUS: Draft

[REQUIREMENT]
UID: AC-3.3
TITLE: AC-3(3) Mandatory Access Control
STATEMENT: >>>
Enforce [organization-defined mandatory access control policy] over the set of covered subjects and objects specified in the policy, and where the policy:

  (a) Is uniformly enforced across the covered subjects and objects within the system;

  (b) Specifies that a subject that has been granted access to information is constrained from doing any of the following;

    (1) Passing the information to unauthorized subjects or objects;

    (2) Granting its privileges to other subjects;

    (3) Changing one or more security attributes (specified by the policy) on subjects, objects, the system, or system components;

    (4) Choosing the security attributes and attribute values (specified by the policy) to be associated with newly created or modified objects; and

    (5) Changing the rules governing access control; and

  (c) Specifies that [subjects] may explicitly be granted [privileges] such that they are not limited by any defined subset (or all) of the above constraints.
<<<
BASELINE: None
STATUS: Draft

[REQUIREMENT]
UID: AC-3.4
TITLE: AC-3(4) Discretionary Access Control
STATEMENT: >>>
Enforce [organization-defined discretionary access control policy] over the set of covered subjects and objects specified in the policy, and where the policy specifies that a subject that has been granted access to information can do one or more of the following:

  (a) Pass the information to any other subjects or objects;

  (b) Grant its privileges to other subjects;

  (c) Change security attributes on subjects, objects, the system, or the system’s components;

  (d) Choose the security attributes to be associated with newly created or revised objects; or

  (e) Change the rules governing access control.
<<<
BASELINE: None
STATUS: Draft

[REQUIREMENT]
UID: AC-3.5
TITLE: AC-3(5) Security-relevant Information
STATEMENT: >>>
Prevent access to [security-relevant information] except during secure, non-operable system states.
<<<
BASELINE: None
STATUS: Draft

[REQUIREMENT]
UID: AC-3.6
TITLE: AC-3(6) Protection of User and System Information
STATEMENT: >>>
Withdrawn. Incorporated into MP-4, SC-28.
<<<
COMMENT: Withdrawn
BASELINE: None
STATUS: Draft

[REQUIREMENT]
UID: AC-3.7
TITLE: AC-3(7) Role-based Access Control
STATEMENT: >>>
Enforce a role-based access control policy over defined subjects and objects and control access based upon [organization-defined roles and users authorized to assume such roles].
<<<
BASELINE: None
STATUS: Draft

[REQUIREMENT]
UID: AC-3.8
TITLE: AC-3(8) Revocation of Access Authorizations
STATEMENT: >>>
Enforce the revocation of access authorizations resulting from changes to the security attributes of subjects and objects based on [rules].
<<<
BASELINE: None
STATUS: Draft

[REQUIREMENT]
UID: AC-3.9
TITLE: AC-3(9) Controlled Release
STATEMENT: >>>
Release information outside of the system only if:

  (a) The receiving [system or system component] provides [controls] ; and

  (b) [controls] are used to validate the appropriateness of the information designated for release.
<<<
BASELINE: None
STATUS: Draft

[REQUIREMENT]
UID: AC-3.10
TITLE: AC-3(10) Audited Override of Access Control Mechanisms
STATEMENT: >>>
Employ an audited override of automated access control mechanisms under [conditions] by [roles].
<<<
BASELINE: None
STATUS: Draft

[REQUIREMENT]
UID: AC-3.11
TITLE: AC-3(11) Restrict Access to Specific Information Types
STATEMENT: >>>
Restrict access to data repositories containing [information types].
<<<
BASELINE: None
STATUS: Draft

[REQUIREMENT]
UID: AC-3.12
TITLE: AC-3(12) Assert and Enforce Application Access
STATEMENT: >>>
(a) Require applications to assert, as part of the installation process, the access needed to the following system applications and functions: [system applications and functions];

(b) Provide an enforcement mechanism to prevent unauthorized access; and

(c) Approve access changes after initial installation of the application.
<<<
BASELINE: None
STATUS: Draft

[REQUIREMENT]
UID: AC-3.13
TITLE: AC-3(13) Attribute-based Access Control
STATEMENT: >>>
Enforce attribute-based access control policy over defined subjects and objects and control access based upon [attributes].
<<<
BASELINE: None
STATUS: Draft

[REQUIREMENT]
UID: AC-3.14
TITLE: AC-3(14) Individual Access
STATEMENT: >>>
Provide [mechanisms] to enable individuals to have access to the following elements of their personally identifiable information: [elements].
<<<
COMMENT: Baselines: Privacy
BASELINE: Privacy
STATUS: Draft

[REQUIREMENT]
UID: AC-3.15
TITLE: AC-3(15) Discretionary and Mandatory Access Control
STATEMENT: >>>
(a) Enforce [organization-defined mandatory access control policy] over the set of covered subjects and objects specified in the policy; and

(b) Enforce [organization-defined discretionary access control policy] over the set of covered subjects and objects specified in the policy.
<<<
BASELINE: None
STATUS: Draft

[REQUIREMENT]
UID: AC-4
TITLE: AC-4 Information Flow Enforcement
STATEMENT: >>>
Enforce approved authorizations for controlling the flow of information within the system and between connected systems based on [information flow control policies].
<<<
COMMENT: Baselines: Moderate, High
BASELINE: Moderate
STATUS: Draft

[REQUIREMENT]
UID: AC-4.1
TITLE: AC-4(1) Object Security and Privacy Attributes
STATEMENT: >>>
Use [organization-defined security and privacy attributes] associated with [organization-defined information, source, and destination objects] to enforce [information flow control policies] as a basis for flow control decisions.
<<<
BASELINE: None
STATUS: Draft

[REQUIREMENT]
UID: AC-4.2
TITLE: AC-4(2) Processing Domains
STATEMENT: >>>
Use protected processing domains to enforce [information flow control policies] as a basis for flow control decisions.
<<<
BASELINE: None
STATUS: Draft

[REQUIREMENT]
UID: AC-4.3
TITLE: AC-4(3) Dynamic Information Flow Control
STATEMENT: >>>
Enforce [information flow control policies].
<<<
BASELINE: None
STATUS: Draft

[REQUIREMENT]
UID: AC-4.4
TITLE: AC-4(4) Flow Control of Encrypted Information
STATEMENT: >>>
Prevent encrypted information from bypassing [information flow control mechanisms] by [ac-04.04_odp.02].
<<<
COMMENT: Baselines: High
BASELINE: High
STATUS: Draft

[REQUIREMENT]
UID: AC-4.5
TITLE: AC-4(5) Embedded Data Types
STATEMENT: >>>
Enforce [limitations] on embedding data types within other data types.
<<<
BASELINE: None
STATUS: Draft

[REQUIREMENT]
UID: AC-4.6
TITLE: AC-4(6) Metadata
STATEMENT: >>>
Enforce information flow control based on [metadata].
<<<
BASELINE: None
STATUS: Draft

[REQUIREMENT]
UID: AC-4.7
TITLE: AC-4(7) One-way Flow Mechanisms
STATEMENT: >>>
Enforce one-way information flows through hardware-based flow control mechanisms.
<<<
BASELINE: None
STATUS: Draft

[REQUIREMENT]
UID: AC-4.8
TITLE: AC-4(8) Security and Privacy Policy Filters
STATEMENT: >>>
(a) Enforce information flow control using [organization-defined security or privacy policy filters] as a basis for flow control decisions for [organization-defined information flows] ; and

(b) [ac-04.08_odp.05] data after a filter processing failure in accordance with [organization-defined security or privacy policy].
<<<
BASELINE: None
STATUS: Draft

[REQUIREMENT]
UID: AC-4.9
TITLE: AC-4(9) Human Reviews
STATEMENT: >>>
Enforce the use of human reviews for [information flows] under the following conditions: [conditions].
<<<
BASELINE: None
STATUS: Draft

[REQUIREMENT]
UID: AC-4.10
TITLE: AC-4(10) Enable and Disable Security or Privacy Policy Filters
STATEMENT: >>>
Provide the capability for privileged administrators to enable and disable [organization-defined security or privacy policy filters] under the following conditions: [organization-defined conditions].
<<<
BASELINE: None
STATUS: Draft

[REQUIREMENT]
UID: AC-4.11
TITLE: AC-4(11) Configuration of Security or Privacy Policy Filters
STATEMENT: >>>
Provide the capability for privileged administrators to configure [organization-defined security or privacy policy filters] to support different security or privacy policies.
<<<
BASELINE: None
STATUS: Draft

[REQUIREMENT]
UID: AC-4.12
TITLE: AC-4(12) Data Type Identifiers
STATEMENT: >>>
When transferring information between different security domains, use [data type identifiers] to validate data essential for information flow decisions.
<<<
BASELINE: None
STATUS: Draft

[REQUIREMENT]
UID: AC-4.13
TITLE: AC-4(13) Decomposition into Policy-relevant Subcomponents
STATEMENT: >>>
When transferring information between different security domains, decompose information into [policy-relevant subcomponents] for submission to policy enforcement mechanisms.
<<<
BASELINE: None
STATUS: Draft

[REQUIREMENT]
UID: AC-4.14
TITLE: AC-4(14) Security or Privacy Policy Filter Constraints
STATEMENT: >>>
When transferring information between different security domains, implement [organization-defined security or privacy policy filters] requiring fully enumerated formats that restrict data structure and content.
<<<
BASELINE: None
STATUS: Draft

[REQUIREMENT]
UID: AC-4.15
TITLE: AC-4(15) Detection of Unsanctioned Information
STATEMENT: >>>
When transferring information between different security domains, examine the information for the presence of [unsanctioned information] and prohibit the transfer of such information in accordance with the [organization-defined security or privacy policy].
<<<
BASELINE: None
STATUS: Draft

[REQUIREMENT]
UID: AC-4.16
TITLE: AC-4(16) Information Transfers on Interconnected Systems
STATEMENT: >>>
Withdrawn. Incorporated into AC-4.
<<<
COMMENT: Withdrawn
BASELINE: None
STATUS: Draft

[REQUIREMENT]
UID: AC-4.17
TITLE: AC-4(17) Domain Authentication
STATEMENT: >>>
Uniquely identify and authenticate source and destination points by [ac-04.17_odp] for information transfer.
<<<
BASELINE: None
STATUS: Draft

[REQUIREMENT]
UID: AC-4.18
TITLE: AC-4(18) Security Attribute Binding
STATEMENT: >>>
Withdrawn. Incorporated into AC-16.
<<<
COMMENT: Withdrawn
BASELINE: None
STATUS: Draft

[REQUIREMENT]
UID: AC-4.19
TITLE: AC-4(19) Validation of Metadata
STATEMENT: >>>
When transferring information between different security domains, implement [organization-defined security or privacy policy filters] on metadata.
<<<
BASELINE: None
STATUS: Draft

[REQUIREMENT]
UID: AC-4.20
TITLE: AC-4(20) Approved Solutions
STATEMENT: >>>
Employ [solutions in approved configurations] to control the flow of [information] across security domains.
<<<
BASELINE: None
STATUS: Draft

[REQUIREMENT]
UID: AC-4.21
TITLE: AC-4(21) Physical or Logical Separation of Information Flows
STATEMENT: >>>
Separate information flows logically or physically using [organization-defined mechanisms and/or techniques] to accomplish [required separations].
<<<
BASELINE: None
STATUS: Draft

[REQUIREMENT]
UID: AC-4.22
TITLE: AC-4(22) Access Only
STATEMENT: >>>
Provide access from a single device to computing platforms, applications, or data residing in multiple different security domains, while preventing information flow between the different security domains.
<<<
BASELINE: None
STATUS: Draft

[REQUIREMENT]
UID: AC-4.23
TITLE: AC-4(23) Modify Non-releasable Information
STATEMENT: >>>
When transferring information between different security domains, modify non-releasable information by implementing [modification action].
<<<
BASELINE: None
STATUS: Draft

[REQUIREMENT]
UID: AC-4.24
TITLE: AC-4(24) Internal Normalized Format
STATEMENT: >>>
When transferring information between different security domains, parse incoming data into an internal normalized format and regenerate the data to be consistent with its intended specification.
<<<
BASELINE: None
STATUS: Draft

[REQUIREMENT]
UID: AC-4.25
TITLE: AC-4(25) Data Sanitization
STATEMENT: >>>
When transferring information between different security domains, sanitize data to minimize [ac-04.25_odp.01] in accordance with [policy].
<<<
BASELINE: None
STATUS: Draft

[REQUIREMENT]
UID: AC-4.26
TITLE: AC-4(26) Audit Filtering Actions
STATEMENT: >>>
When transferring information between different security domains, record and audit content filtering actions and results for the information being filtered.
<<<
BASELINE: None
STATUS: Draft

[REQUIREMENT]
UID: AC-4.27
TITLE: AC-4(27) Redundant/Independent Filtering Mechanisms
STATEMENT: >>>
When transferring information between different security domains, implement content filtering solutions that provide redundant and independent filtering mechanisms for each data type.
<<<
BASELINE: None
STATUS: Draft

[REQUIREMENT]
UID: AC-4.28
TITLE: AC-4(28) Linear Filter Pipelines
STATEMENT: >>>
When transferring information between different security domains, implement a linear content filter pipeline that is enforced with discretionary and mandatory access controls.
<<<
BASELINE: None
STATUS: Draft

[REQUIREMENT]
UID: AC-4.29
TITLE: AC-4(29) Filter Orchestration Engines
STATEMENT: >>>
When transferring information between different security domains, employ content filter orchestration engines to ensure that:

  (a) Content filtering mechanisms successfully complete execution without errors; and

  (b) Content filtering actions occur in the correct order and comply with [policy].
<<<
BASELINE: None
STATUS: Draft

[REQUIREMENT]
UID: AC-4.30
TITLE: AC-4(30) Filter Mechanisms Using Multiple Processes
STATEMENT: >>>
When transferring information between different security domains, implement content filtering mechanisms using multiple processes.
<<<
BASELINE: None
STATUS: Draft

[REQUIREMENT]
UID: AC-4.31
TITLE: AC-4(31) Failed Content Transfer Prevention
STATEMENT: >>>
When transferring information between different security domains, prevent the transfer of failed content to the receiving domain.
<<<
BASELINE: None
STATUS: Draft

[REQUIREMENT]
UID: AC-4.32
TITLE: AC-4(32) Process Requirements for Information Transfer
STATEMENT: >>>
When transferring information between different security domains, the process that transfers information between filter pipelines:

  (a) Does not filter message content;

  (b) Validates filtering metadata;

  (c) Ensures the content associated with the filtering metadata has successfully completed filtering; and

  (d) Transfers the content to the destination filter pipeline.
<<<
BASELINE: None
STATUS: Draft

[REQUIREMENT]
UID: AC-5
TITLE: AC-5 Separation of Duties
STATEMENT: >>>
a. Identify and document [duties of individuals] ; and

b. Define system access authorizations to support separation of duties.
<<<
COMMENT: Baselines: Moderate, High
BASELINE: Moderate
STATUS: Draft

[REQUIREMENT]
UID: AC-6
TITLE: AC-6 Least Privilege
STATEMENT: >>>
Employ the principle of least privilege, allowing only authorized accesses for users (or processes acting on behalf of users) that are necessary to accomplish assigned organizational tasks.
<<<
COMMENT: Baselines: Moderate, High
BASELINE: Moderate
STATUS: Draft

[REQUIREMENT]
UID: AC-6.1
TITLE: AC-6(1) Authorize Access to Security Functions
STATEMENT: >>>
Authorize access for [individuals and roles] to:

  (a) [organization-defined security functions (deployed in hardware, software, and firmware)] ; and

  (b) [security-relevant information].
<<<
COMMENT: Baselines: Moderate, High
BASELINE: Moderate
STATUS: Draft

[REQUIREMENT]
UID: AC-6.2
TITLE: AC-6(2) Non-privileged Access for Nonsecurity Functions
STATEMENT: >>>
Require that users of system accounts (or roles) with access to [security functions or security-relevant information] use non-privileged accounts or roles, when accessing nonsecurity functions.
<<<
COMMENT: Baselines: Moderate, High
BASELINE: Moderate
STATUS: Draft

[REQUIREMENT]
UID: AC-6.3
TITLE: AC-6(3) Network Access to Privileged Commands
STATEMENT: >>>
Authorize network access to [privileged commands] only for [compelling operational needs] and document the rationale for such access in the security plan for the system.
<<<
COMMENT: Baselines: High
BASELINE: High
STATUS: Draft

[REQUIREMENT]
UID: AC-6.4
TITLE: AC-6(4) Separate Processing Domains
STATEMENT: >>>
Provide separate processing domains to enable finer-grained allocation of user privileges.
<<<
BASELINE: None
STATUS: Draft

[REQUIREMENT]
UID: AC-6.5
TITLE: AC-6(5) Privileged Accounts
STATEMENT: >>>
Restrict privileged accounts on the system to [personnel or roles].
<<<
COMMENT: Baselines: Moderate, High
BASELINE: Moderate
STATUS: Draft

[REQUIREMENT]
UID: AC-6.6
TITLE: AC-6(6) Privileged Access by Non-organizational Users
STATEMENT: >>>
Prohibit privileged access to the system by non-organizational users.
<<<
BASELINE: None
STATUS: Draft

[REQUIREMENT]
UID: AC-6.7
TITLE: AC-6(7) Review of User Privileges
STATEMENT: >>>
(a) Review [frequency] the privileges assigned to [roles and classes] to validate the need for such privileges; and

(b) Reassign or remove privileges, if necessary, to correctly reflect organizational mission and business needs.
<<<
COMMENT: Baselines: Moderate, High
BASELINE: Moderate
STATUS: Draft

[REQUIREMENT]
UID: AC-6.8
TITLE: AC-6(8) Privilege Levels for Code Execution
STATEMENT: >>>
Prevent the following software from executing at higher privilege levels than users executing the software: [software].
<<<
BASELINE: None
STATUS: Draft

[REQUIREMENT]
UID: AC-6.9
TITLE: AC-6(9) Log Use of Privileged Functions
STATEMENT: >>>
Log the execution of privileged functions.
<<<
COMMENT: Baselines: Moderate, High
BASELINE: Moderate
STATUS: Draft

[REQUIREMENT]
UID: AC-6.10
TITLE: AC-6(10) Prohibit Non-privileged Users from Executing Privileged Functions
STATEMENT: >>>
Prevent non-privileged users from executing privileged functions.
<<<
COMMENT: Baselines: Moderate, High
BASELINE: Moderate
STATUS: Draft

[REQUIREMENT]
UID: AC-7
TITLE: AC-7 Unsuccessful Logon Attempts
STATEMENT: >>>
a. Enforce a limit of [number] consecutive invalid logon attempts by a user during a [time period] ; and

b. Automatically [ac-07_odp.03] when the maximum number of unsuccessful attempts is exceeded.
<<<
COMMENT: Baselines: Low, Moderate, High
BASELINE: Low
STATUS: Draft

[REQUIREMENT]
UID: AC-7.1
TITLE: AC-7(1) Automatic Account Lock
STATEMENT: >>>
Withdrawn. Incorporated into AC-7.
<<<
COMMENT: Withdrawn
BASELINE: None
STATUS: Draft

[REQUIREMENT]
UID: AC-7.2
TITLE: AC-7(2) Purge or Wipe Mobile Device
STATEMENT: >>>
Purge or wipe information from [mobile devices] based on [purging or wiping requirements and techniques] after [number] consecutive, unsuccessful device logon attempts.
<<<
BASELINE: None
STATUS: Draft

[REQUIREMENT]
UID: AC-7.3
TITLE: AC-7(3) Biometric Attempt Limiting
STATEMENT: >>>
Limit the number of unsuccessful biometric logon attempts to [number].
<<<
BASELINE: None
STATUS: Draft

[REQUIREMENT]
UID: AC-7.4
TITLE: AC-7(4) Use of Alternate Authentication Factor
STATEMENT: >>>
(a) Allow the use of [authentication factors] that are different from the primary authentication factors after the number of organization-defined consecutive invalid logon attempts have been exceeded; and

(b) Enforce a limit of [number] consecutive invalid logon attempts through use of the alternative factors by a user during a [time period].
<<<
BASELINE: None
STATUS: Draft

[REQUIREMENT]
UID: AC-8
TITLE: AC-8 System Use Notification
STATEMENT: >>>
a. Display [system use notification] to users before granting access to the system that provides privacy and security notices consistent with applicable laws, executive orders, directives, regulations, policies, standards, and guidelines and state that:

  1. Users are accessing a U.S. Government system;

  2. System usage may be monitored, recorded, and subject to audit;

  3. Unauthorized use of the system is prohibited and subject to criminal and civil penalties; and

  4. Use of the system indicates consent to monitoring and recording;

b. Retain the notification message or banner on the screen until users acknowledge the usage conditions and take explicit actions to log on to or further access the system; and

c. For publicly accessible systems:

  1. Display system use information [conditions] , before granting further access to the publicly accessible system;

  2. Display references, if any, to monitoring, recording, or auditing that are consistent with privacy accommodations for such systems that generally prohibit those activities; and

  3. Include a description of the authorized uses of the system.
<<<
COMMENT: Baselines: Low, Moderate, High
BASELINE: Low
STATUS: Draft

[REQUIREMENT]
UID: AC-9
TITLE: AC-9 Previous Logon Notification
STATEMENT: >>>
Notify the user, upon successful logon to the system, of the date and time of the last logon.
<<<
BASELINE: None
STATUS: Draft

[REQUIREMENT]
UID: AC-9.1
TITLE: AC-9(1) Unsuccessful Logons
STATEMENT: >>>
Notify the user, upon successful logon, of the number of unsuccessful logon attempts since the last successful logon.
<<<
BASELINE: None
STATUS: Draft

[REQUIREMENT]
UID: AC-9.2
TITLE: AC-9(2) Successful and Unsuccessful Logons
STATEMENT: >>>
Notify the user, upon successful logon, of the number of [ac-09.02_odp.01] during [time period].
<<<
BASELINE: None
STATUS: Draft

[REQUIREMENT]
UID: AC-9.3
TITLE: AC-9(3) Notification of Account Changes
STATEMENT: >>>
Notify the user, upon successful logon, of changes to [security-related characteristics or parameters] during [time period].
<<<
BASELINE: None
STATUS: Draft

[REQUIREMENT]
UID: AC-9.4
TITLE: AC-9(4) Additional Logon Information
STATEMENT: >>>
Notify the user, upon successful logon, of the following additional information: [additional information].
<<<
BASELINE: None
STATUS: Draft

[REQUIREMENT]
UID: AC-10
TITLE: AC-10 Concurrent Session Control
STATEMENT: >>>
Limit the number of concurrent sessions for each [account and/or account types] to [number].
<<<
COMMENT: Baselines: High
BASELINE: High
STATUS: Draft

[REQUIREMENT]
UID: AC-11
TITLE: AC-11 Device Lock
STATEMENT: >>>
a. Prevent further access to the system by [ac-11_odp.01] ; and

b. Retain the device lock until the user reestablishes access using established identification and authentication procedures.
<<<
COMMENT: Baselines: Moderate, High
BASELINE: Moderate
STATUS: Draft

[REQUIREMENT]
UID: AC-11.1
TITLE: AC-11(1) Pattern-hiding Displays
STATEMENT: >>>
Conceal, via the device lock, information previously visible on the display with a publicly viewable image.
<<<
COMMENT: Baselines: Moderate, High
BASELINE: Moderate
STATUS: Draft

[REQUIREMENT]
UID: AC-12
TITLE: AC-12 Session Termination
STATEMENT: >>>
Automatically terminate a user session after [conditions or trigger events].
<<<
COMMENT: Baselines: Moderate, High
BASELINE: Moderate
STATUS: Draft

[REQUIREMENT]
UID: AC-12.1
TITLE: AC-12(1) User-initiated Logouts
STATEMENT: >>>
Provide a logout capability for user-initiated communications sessions whenever authentication is used to gain access to [information resources].
<<<
BASELINE: None
STATUS: Draft

[REQUIREMENT]
UID: AC-12.2
TITLE: AC-12(2) Termination Message
STATEMENT: >>>
Display an explicit logout message to users indicating the termination of authenticated communications sessions.
<<<
BASELINE: None
STATUS: Draft

[REQUIREMENT]
UID: AC-12.3
TITLE: AC-12(3) Timeout Warning Message
STATEMENT: >>>
Display an explicit message to users indicating that the session will end in [time].
<<<
BASELINE: None
STATUS: Draft

[REQUIREMENT]
UID: AC-13
TITLE: AC-13 Supervision and Review — Access Control
STATEMENT: >>>
Withdrawn. Incorporated into AC-2, AU-6.
<<<
COMMENT: Withdrawn
BASELINE: None
STATUS: Draft

[REQUIREMENT]
UID: AC-14
TITLE: AC-14 Permitted Actions Without Identification or Authentication
STATEMENT: >>>
a. Identify [user actions] that can be performed on the system without identification or authentication consistent with organizational mission and business functions; and

b. Document and provide supporting rationale in the security plan for the system, user actions not requiring identification or authentication.
<<<
COMMENT: Baselines: Low, Moderate, High
BASELINE: Low
STATUS: Draft

[REQUIREMENT]
UID: AC-14.1
TITLE: AC-14(1) Necessary Uses
STATEMENT: >>>
Withdrawn. Incorporated into AC-14.
<<<
COMMENT: Withdrawn
BASELINE: None
STATUS: Draft

[REQUIREMENT]
UID: AC-15
TITLE: AC-15 Automated Marking
STATEMENT: >>>
Withdrawn. Incorporated into MP-3.
<<<
COMMENT: Withdrawn
BASELINE: None
STATUS: Draft

[REQUIREMENT]
UID: AC-16
TITLE: AC-16 Security and Privacy Attributes
STATEMENT: >>>
a. Provide the means to associate [organization-defined types of security and privacy attributes] with [organization-defined security and privacy attribute values] for information in storage, in process, and/or in transmission;

b. Ensure that the attribute associations are made and retained with the information;

c. Establish the following permitted security and privacy attributes from the attributes defined in [AC-16a](#ac-16_smt.a) for [organization-defined systems]: [organization-defined security and privacy attributes];

d. Determine the following permitted attribute values or ranges for each of the established attributes: [attribute values or ranges];

e. Audit changes to attributes; and

f. Review [organization-defined security and privacy attributes] for applicability [organization-defined frequency].
<<<
BASELINE: None
STATUS: Draft

[REQUIREMENT]
UID: AC-16.1
TITLE: AC-16(1) Dynamic Attribute Association
STATEMENT: >>>
Dynamically associate security and privacy attributes with [organization-defined subjects and objects] in accordance with the following security and privacy policies as information is created and combined: [organization-defined security and privacy policies].
<<<
BASELINE: None
STATUS: Draft

[REQUIREMENT]
UID: AC-16.2
TITLE: AC-16(2) Attribute Value Changes by Authorized Individuals
STATEMENT: >>>
Provide authorized individuals (or processes acting on behalf of individuals) the capability to define or change the value of associated security and privacy attributes.
<<<
BASELINE: None
STATUS: Draft

[REQUIREMENT]
UID: AC-16.3
TITLE: AC-16(3) Maintenance of Attribute Associations by System
STATEMENT: >>>
Maintain the association and integrity of [organization-defined security and privacy attributes] to [organization-defined subjects and objects].
<<<
BASELINE: None
STATUS: Draft

[REQUIREMENT]
UID: AC-16.4
TITLE: AC-16(4) Association of Attributes by Authorized Individuals
STATEMENT: >>>
Provide the capability to associate [organization-defined security and privacy attributes] with [organization-defined subjects and objects] by authorized individuals (or processes acting on behalf of individuals).
<<<
BASELINE: None
STATUS: Draft

[REQUIREMENT]
UID: AC-16.5
TITLE: AC-16(5) Attribute Displays on Objects to Be Output
STATEMENT: >>>
Display security and privacy attributes in human-readable form on each object that the system transmits to output devices to identify [instructions] using [naming conventions].
<<<
BASELINE: None
STATUS: Draft

[REQUIREMENT]
UID: AC-16.6
TITLE: AC-16(6) Maintenance of Attribute Association
STATEMENT: >>>
Require personnel to associate and maintain the association of [organization-defined security and privacy attributes] with [organization-defined subjects and objects] in accordance with [organization-defined security and privacy policies].
<<<
BASELINE: None
STATUS: Draft

[REQUIREMENT]
UID: AC-16.7
TITLE: AC-16(7) Consistent Attribute Interpretation
STATEMENT: >>>
Provide a consistent interpretation of security and privacy attributes transmitted between distributed system components.
<<<
BASELINE: None
STATUS: Draft

[REQUIREMENT]
UID: AC-16.8
TITLE: AC-16(8) Association Techniques and Technologies
STATEMENT: >>>
Implement [organization-defined techniques and technologies] in associating security and privacy attributes to information.
<<<
BASELINE: None
STATUS: Draft

[REQUIREMENT]
UID: AC-16.9
TITLE: AC-16(9) Attribute Reassignment — Regrading Mechanisms
STATEMENT: >>>
Change security and privacy attributes associated with information only via regrading mechanisms validated using [organization-defined techniques or procedures].
<<<
BASELINE: None
STATUS: Draft

[REQUIREMENT]
UID: AC-16.10
TITLE: AC-16(10) Attribute Configuration by Authorized Individuals
STATEMENT: >>>
Provide authorized individuals the capability to define or change the type and value of security and privacy attributes available for association with subjects and objects.
<<<
BASELINE: None
STATUS: Draft

[REQUIREMENT]
UID: AC-17
TITLE: AC-17 Remote Access
STATEMENT: >>>
a. Establish and document usage restrictions, configuration/connection requirements, and implementation guidance for each type of remote access allowed; and

b. Authorize each type of remote access to the system prior to allowing such connections.
<<<
COMMENT: Baselines: Low, Moderate, High
BASELINE: Low
STATUS: Draft

[REQUIREMENT]
UID: AC-17.1
TITLE: AC-17(1) Monitoring and Control
STATEMENT: >>>
Employ automated mechanisms to monitor and control remote access methods.
<<<
COMMENT: Baselines: Moderate, High
BASELINE: Moderate
STATUS: Draft

[REQUIREMENT]
UID: AC-17.2
TITLE: AC-17(2) Protection of Confidentiality and Integrity Using Encryption
STATEMENT: >>>
Implement cryptographic mechanisms to protect the confidentiality and integrity of remote access sessions.
<<<
COMMENT: Baselines: Moderate, High
BASELINE: Moderate
STATUS: Draft

[REQUIREMENT]
UID: AC-17.3
TITLE: AC-17(3) Managed Access Control Points
STATEMENT: >>>
Route remote accesses through authorized and managed network access control points.
<<<
COMMENT: Baselines: Moderate, High
BASELINE: Moderate
STATUS: Draft

[REQUIREMENT]
UID: AC-17.4
TITLE: AC-17(4) Privileged Commands and Access
STATEMENT: >>>
(a) Authorize the execution of privileged commands and access to security-relevant information via remote access only in a format that provides assessable evidence and for the following needs: [organization-defined needs] ; and

(b) Document the rationale for remote access in the security plan for the system.
<<<
COMMENT: Baselines: Moderate, High
BASELINE: Moderate
STATUS: Draft

[REQUIREMENT]
UID: AC-17.5
TITLE: AC-17(5) Monitoring for Unauthorized Connections
STATEMENT: >>>
Withdrawn. Incorporated into SI-4.
<<<
COMMENT: Withdrawn
BASELINE: None
STATUS: Draft

[REQUIREMENT]
UID: AC-17.6
TITLE: AC-17(6) Protection of Mechanism Information
STATEMENT: >>>
Protect information about remote access mechanisms from unauthorized use and disclosure.
<<<
BASELINE: None
STATUS: Draft

[REQUIREMENT]
UID: AC-17.7
TITLE: AC-17(7) Additional Protection for Security Function Access
STATEMENT: >>>
Withdrawn. Incorporated into AC-3.10.
<<<
COMMENT: Withdrawn
BASELINE: None
STATUS: Draft

[REQUIREMENT]
UID: AC-17.8
TITLE: AC-17(8) Disable Nonsecure Network Protocols
STATEMENT: >>>
Withdrawn. Incorporated into CM-7.
<<<
COMMENT: Withdrawn
BASELINE: None
STATUS: Draft

[REQUIREMENT]
UID: AC-17.9
TITLE: AC-17(9) Disconnect or Disable Access
STATEMENT: >>>
Provide the capability to disconnect or disable remote access to the system within [time period].
<<<
BASELINE: None
STATUS: Draft

[REQUIREMENT]
UID: AC-17.10
TITLE: AC-17(10) Authenticate Remote Commands
STATEMENT: >>>
Implement [mechanisms] to authenticate [remote commands].
<<<
BASELINE: None
STATUS: Draft

[REQUIREMENT]
UID: AC-18
TITLE: AC-18 Wireless Access
STATEMENT: >>>
a. Establish configuration requirements, connection requirements, and implementation guidance for each type of wireless access; and

b. Authorize each type of wireless access to the system prior to allowing such connections.
<<<
COMMENT: Baselines: Low, Moderate, High
BASELINE: Low
STATUS: Draft

[REQUIREMENT]
UID: AC-18.1
TITLE: AC-18(1) Authentication and Encryption
STATEMENT: >>>
Protect wireless access to the system using authentication of [ac-18.01_odp] and encryption.
<<<
COMMENT: Baselines: Moderate, High
BASELINE: Moderate
STATUS: Draft

[REQUIREMENT]
UID: AC-18.2
TITLE: AC-18(2) Monitoring Unauthorized Connections
STATEMENT: >>>
Withdrawn. Incorporated into SI-4.
<<<
COMMENT: Withdrawn
BASELINE: None
STATUS: Draft

[REQUIREMENT]
UID: AC-18.3
TITLE: AC-18(3) Disable Wireless Networking
STATEMENT: >>>
Disable, when not intended for use, wireless networking capabilities embedded within system components prior to issuance and deployment.
<<<
COMMENT: Baselines: Moderate, High
BASELINE: Moderate
STATUS: Draft

[REQUIREMENT]
UID: AC-18.4
TITLE: AC-18(4) Restrict Configurations by Users
STATEMENT: >>>
Identify and explicitly authorize users allowed to independently configure wireless networking capabilities.
<<<
COMMENT: Baselines: High
BASELINE: High
STATUS: Draft

[REQUIREMENT]
UID: AC-18.5
TITLE: AC-18(5) Antennas and Transmission Power Levels
STATEMENT: >>>
Select radio antennas and calibrate transmission power levels to reduce the probability that signals from wireless access points can be received outside of organization-controlled boundaries.
<<<
COMMENT: Baselines: High
BASELINE: High
STATUS: Draft

[REQUIREMENT]
UID: AC-19
TITLE: AC-19 Access Control for Mobile Devices
STATEMENT: >>>
a. Establish configuration requirements, connection requirements, and implementation guidance for organization-controlled mobile devices, to include when such devices are outside of controlled areas; and

b. Authorize the connection of mobile devices to organizational systems.
<<<
COMMENT: Baselines: Low, Moderate, High
BASELINE: Low
STATUS: Draft

[REQUIREMENT]
UID: AC-19.1
TITLE: AC-19(1) Use of Writable and Portable Storage Devices
STATEMENT: >>>
Withdrawn. Incorporated into MP-7.
<<<
COMMENT: Withdrawn
BASELINE: None
STATUS: Draft

[REQUIREMENT]
UID: AC-19.2
TITLE: AC-19(2) Use of Personally Owned Portable Storage Devices
STATEMENT: >>>
Withdrawn. Incorporated into MP-7.
<<<
COMMENT: Withdrawn
BASELINE: None
STATUS: Draft

[REQUIREMENT]
UID: AC-19.3
TITLE: AC-19(3) Use of Portable Storage Devices with No Identifiable Owner
STATEMENT: >>>
Withdrawn. Incorporated into MP-7.
<<<
COMMENT: Withdrawn
BASELINE: None
STATUS: Draft

[REQUIREMENT]
UID: AC-19.4
TITLE: AC-19(4) Restrictions for Classified Information
STATEMENT: >>>
(a) Prohibit the use of unclassified mobile devices in facilities containing systems processing, storing, or transmitting classified information unless specifically permitted by the authorizing official; and

(b) Enforce the following restrictions on individuals permitted by the authorizing official to use unclassified mobile devices in facilities containing systems processing, storing, or transmitting classified information:

  (1) Connection of unclassified mobile devices to classified systems is prohibited;

  (2) Connection of unclassified mobile devices to unclassified systems requires approval from the authorizing official;

  (3) Use of internal or external modems or wireless interfaces within the unclassified mobile devices is prohibited; and

  (4) Unclassified mobile devices and the information stored on those devices are subject to random reviews and inspections by [security officials] , and if classified information is found, the incident handling policy is followed.

(c) Restrict the connection of classified mobile devices to classified systems in accordance with [security policies].
<<<
BASELINE: None
STATUS: Draft

[REQUIREMENT]
UID: AC-19.5
TITLE: AC-19(5) Full Device or Container-based Encryption
STATEMENT: >>>
Employ [ac-19.05_odp.01] to protect the confidentiality and integrity of information on [mobile devices].
<<<
COMMENT: Baselines: Moderate, High
BASELINE: Moderate
STATUS: Draft

[REQUIREMENT]
UID: AC-20
TITLE: AC-20 Use of External Systems
STATEMENT: >>>
a. [ac-20_odp.01] , consistent with the trust relationships established with other organizations owning, operating, and/or maintaining external systems, allowing authorized individuals to:

  1. Access the system from external systems; and

  2. Process, store, or transmit organization-controlled information using external systems; or

b. Prohibit the use of [prohibited types of external systems].
<<<
COMMENT: Baselines: Low, Moderate, High
BASELINE: Low
STATUS: Draft

[REQUIREMENT]
UID: AC-20.1
TITLE: AC-20(1) Limits on Authorized Use
STATEMENT: >>>
Permit authorized individuals to use an external system to access the system or to process, store, or transmit organization-controlled information only after:

  (a) Verification of the implementation of controls on the external system as specified in the organization’s security and privacy policies and security and privacy plans; or

  (b) Retention of approved system connection or processing agreements with the organizational entity hosting the external system.
<<<
COMMENT: Baselines: Moderate, High
BASELINE: Moderate
STATUS: Draft

[REQUIREMENT]
UID: AC-20.2
TITLE: AC-20(2) Portable Storage Devices — Restricted Use
STATEMENT: >>>
Restrict the use of organization-controlled portable storage devices by authorized individuals on external systems using [restrictions].
<<<
COMMENT: Baselines: Moderate, High
BASELINE: Moderate
STATUS: Draft

[REQUIREMENT]
UID: AC-20.3
TITLE: AC-20(3) Non-organizationally Owned Systems — Restricted Use
STATEMENT: >>>
Restrict the use of non-organizationally owned systems or system components to process, store, or transmit organizational information using [restrictions].
<<<
BASELINE: None
STATUS: Draft

[REQUIREMENT]
UID: AC-20.4
TITLE: AC-20(4) Network Accessible Storage Devices — Prohibited Use
STATEMENT: >>>
Prohibit the use of [network-accessible storage devices] in external systems.
<<<
BASELINE: None
STATUS: Draft

[REQUIREMENT]
UID: AC-20.5
TITLE: AC-20(5) Portable Storage Devices — Prohibited Use
STATEMENT: >>>
Prohibit the use of organization-controlled portable storage devices by authorized individuals on external systems.
<<<
BASELINE: None
STATUS: Draft

[REQUIREMENT]
UID: AC-21
TITLE: AC-21 Information Sharing
STATEMENT: >>>
a. Enable authorized users to determine whether access authorizations assigned to a sharing partner match the information’s access and use restrictions for [information-sharing circumstances] ; and

b. Employ [automated mechanisms] to assist users in making information sharing and collaboration decisions.
<<<
COMMENT: Baselines: Moderate, High
BASELINE: Moderate
STATUS: Draft

[REQUIREMENT]
UID: AC-21.1
TITLE: AC-21(1) Automated Decision Support
STATEMENT: >>>
Employ [automated mechanisms] to enforce information-sharing decisions by authorized users based on access authorizations of sharing partners and access restrictions on information to be shared.
<<<
BASELINE: None
STATUS: Draft

[REQUIREMENT]
UID: AC-21.2
TITLE: AC-21(2) Information Search and Retrieval
STATEMENT: >>>
Implement information search and retrieval services that enforce [information-sharing restrictions].
<<<
BASELINE: None
STATUS: Draft

[REQUIREMENT]
UID: AC-22
TITLE: AC-22 Publicly Accessible Content
STATEMENT: >>>
a. Designate individuals authorized to make information publicly accessible;

b. Train authorized individuals to ensure that publicly accessible information does not contain nonpublic information;

c. Review the proposed content of information prior to posting onto the publicly accessible system to ensure that nonpublic information is not included; and

d. Review the content on the publicly accessible system for nonpublic information [frequency] and remove such information, if discovered.
<<<
COMMENT: Baselines: Low, Moderate, High
BASELINE: Low
STATUS: Draft

[REQUIREMENT]
UID: AC-23
TITLE: AC-23 Data Mining Protection
STATEMENT: >>>
Employ [techniques] for [data storage objects] to detect and protect against unauthorized data mining.
<<<
BASELINE: None
STATUS: Draft

[REQUIREMENT]
UID: AC-24
TITLE: AC-24 Access Control Decisions
STATEMENT: >>>
[ac-24_odp.01] to ensure [access control decisions] are applied to each access request prior to access enforcement.
<<<
BASELINE: None
STATUS: Draft

[REQUIREMENT]
UID: AC-24.1
TITLE: AC-24(1) Transmit Access Authorization Information
STATEMENT: >>>
Transmit [access authorization information] using [controls] to [systems] that enforce access control decisions.
<<<
BASELINE: None
STATUS: Draft

[REQUIREMENT]
UID: AC-24.2
TITLE: AC-24(2) No User or Process Identity
STATEMENT: >>>
Enforce access control decisions based on [organization-defined security or privacy attributes] that do not include the identity of the user or process acting on behalf of the user.
<<<
BASELINE: None
STATUS: Draft

[REQUIREMENT]
UID: AC-25
TITLE: AC-25 Reference Monitor
STATEMENT: >>>
Implement a reference monitor for [access control policies] that is tamperproof, always invoked, and small enough to be subject to analysis and testing, the completeness of which can be assured.
<<<
BASELINE: None
STATUS: Draft

[[/SECTION]]

[[SECTION]]
UID: NIST-AT
TITLE: AT — Awareness and Training

[REQUIREMENT]
UID: AT-1
TITLE: AT-1 Policy and Procedures
STATEMENT: >>>
a. Develop, document, and disseminate to [organization-defined personnel or roles]:

  1. [at-01_odp.03] awareness and training policy that:

    (a) Addresses purpose, scope, roles, responsibilities, management commitment, coordination among organizational entities, and compliance; and

    (b) Is consistent with applicable laws, executive orders, directives, regulations, policies, standards, and guidelines; and

  2. Procedures to facilitate the implementation of the awareness and training policy and the associated awareness and training controls;

b. Designate an [official] to manage the development, documentation, and dissemination of the awareness and training policy and procedures; and

c. Review and update the current awareness and training:

  1. Policy [frequency] and following [events] ; and

  2. Procedures [frequency] and following [events].
<<<
COMMENT: Baselines: Low, Moderate, High, Privacy
BASELINE: Low
STATUS: Draft

[REQUIREMENT]
UID: AT-2
TITLE: AT-2 Literacy Training and Awareness
STATEMENT: >>>
a. Provide security and privacy literacy training to system users (including managers, senior executives, and contractors):

  1. As part of initial training for new users and [organization-defined frequency] thereafter; and

  2. When required by system changes or following [organization-defined events];

b. Employ the following techniques to increase the security and privacy awareness of system users [awareness techniques];

c. Update literacy training and awareness content [frequency] and following [events] ; and

d. Incorporate lessons learned from internal or external security incidents or breaches into literacy training and awareness techniques.
<<<
COMMENT: Baselines: Low, Moderate, High, Privacy
BASELINE: Low
STATUS: Draft

[REQUIREMENT]
UID: AT-2.1
TITLE: AT-2(1) Practical Exercises
STATEMENT: >>>
Provide practical exercises in literacy training that simulate events and incidents.
<<<
BASELINE: None
STATUS: Draft

[REQUIREMENT]
UID: AT-2.2
TITLE: AT-2(2) Insider Threat
STATEMENT: >>>
Provide literacy training on recognizing and reporting potential indicators of insider threat.
<<<
COMMENT: Baselines: Low, Moderate, High
BASELINE: Low
STATUS: Draft

[REQUIREMENT]
UID: AT-2.3
TITLE: AT-2(3) Social Engineering and Mining
STATEMENT: >>>
Provide literacy training on recognizing and reporting potential and actual instances of social engineering and social mining.
<<<
COMMENT: Baselines: Moderate, High
BASELINE: Moderate
STATUS: Draft

[REQUIREMENT]
UID: AT-2.4
TITLE: AT-2(4) Suspicious Communications and Anomalous System Behavior
STATEMENT: >>>
Provide literacy training on recognizing suspicious communications and anomalous behavior in organizational systems using [indicators of malicious code].
<<<
BASELINE: None
STATUS: Draft

[REQUIREMENT]
UID: AT-2.5
TITLE: AT-2(5) Advanced Persistent Threat
STATEMENT: >>>
Provide literacy training on the advanced persistent threat.
<<<
BASELINE: None
STATUS: Draft

[REQUIREMENT]
UID: AT-2.6
TITLE: AT-2(6) Cyber Threat Environment
STATEMENT: >>>
(a) Provide literacy training on the cyber threat environment; and

(b) Reflect current cyber threat information in system operations.
<<<
BASELINE: None
STATUS: Draft

[REQUIREMENT]
UID: AT-3
TITLE: AT-3 Role-based Training
STATEMENT: >>>
a. Provide role-based security and privacy training to personnel with the following roles and responsibilities: [organization-defined roles and responsibilities]:

  1. Before authorizing access to the system, information, or performing assigned duties, and [frequency] thereafter; and

  2. When required by system changes;

b. Update role-based training content [frequency] and following [events] ; and

c. Incorporate lessons learned from internal or external security incidents or breaches into role-based training.
<<<
COMMENT: Baselines: Low, Moderate, High, Privacy
BASELINE: Low
STATUS: Draft

[REQUIREMENT]
UID: AT-3.1
TITLE: AT-3(1) Environmental Controls
STATEMENT: >>>
Provide [personnel or roles] with initial and [frequency] training in the employment and operation of environmental controls.
<<<
BASELINE: None
STATUS: Draft

[REQUIREMENT]
UID: AT-3.2
TITLE: AT-3(2) Physical Security Controls
STATEMENT: >>>
Provide [personnel or roles] with initial and [frequency] training in the employment and operation of physical security controls.
<<<
BASELINE: None
STATUS: Draft

[REQUIREMENT]
UID: AT-3.3
TITLE: AT-3(3) Practical Exercises
STATEMENT: >>>
Provide practical exercises in security and privacy training that reinforce training objectives.
<<<
BASELINE: None
STATUS: Draft

[REQUIREMENT]
UID: AT-3.4
TITLE: AT-3(4) Suspicious Communications and Anomalous System Behavior
STATEMENT: >>>
Withdrawn.
<<<
COMMENT: Withdrawn
BASELINE: None
STATUS: Draft

[REQUIREMENT]
UID: AT-3.5
TITLE: AT-3(5) Processing Personally Identifiable Information
STATEMENT: >>>
Provide [personnel or roles] with initial and [frequency] training in the employment and operation of personally identifiable information processing and transparency controls.
<<<
COMMENT: Baselines: Privacy
BASELINE: Privacy
STATUS: Draft

[REQUIREMENT]
UID: AT-4
TITLE: AT-4 Training Records
STATEMENT: >>>
a. Document and monitor information security and privacy training activities, including security and privacy awareness training and specific role-based security and privacy training; and

b. Retain individual training records for [time period].
<<<
COMMENT: Baselines: Low, Moderate, High, Privacy
BASELINE: Low
STATUS: Draft

[REQUIREMENT]
UID: AT-5
TITLE: AT-5 Contacts with Security Groups and Associations
STATEMENT: >>>
Withdrawn. Incorporated into PM-15.
<<<
COMMENT: Withdrawn
BASELINE: None
STATUS: Draft

[REQUIREMENT]
UID: AT-6
TITLE: AT-6 Training Feedback
STATEMENT: >>>
Provide feedback on organizational training results to the following personnel [frequency]: [personnel].
<<<
BASELINE: None
STATUS: Draft

[[/SECTION]]

[[SECTION]]
UID: NIST-AU
TITLE: AU — Audit and Accountability

[REQUIREMENT]
UID: AU-1
TITLE: AU-1 Policy and Procedures
STATEMENT: >>>
a. Develop, document, and disseminate to [organization-defined personnel or roles]:

  1. [au-01_odp.03] audit and accountability policy that:

    (a) Addresses purpose, scope, roles, responsibilities, management commitment, coordination among organizational entities, and compliance; and

    (b) Is consistent with applicable laws, executive orders, directives, regulations, policies, standards, and guidelines; and

  2. Procedures to facilitate the implementation of the audit and accountability policy and the associated audit and accountability controls;

b. Designate an [official] to manage the development, documentation, and dissemination of the audit and accountability policy and procedures; and

c. Review and update the current audit and accountability:

  1. Policy [frequency] and following [events] ; and

  2. Procedures [frequency] and following [events].
<<<
COMMENT: Baselines: Low, Moderate, High, Privacy
BASELINE: Low
STATUS: Draft

[REQUIREMENT]
UID: AU-2
TITLE: AU-2 Event Logging
STATEMENT: >>>
a. Identify the types of events that the system is capable of logging in support of the audit function: [event types];

b. Coordinate the event logging function with other organizational entities requiring audit-related information to guide and inform the selection criteria for events to be logged;

c. Specify the following event types for logging within the system: [organization-defined event types (subset of the event types defined in [AU-2a.](#au-2_smt.a)) along with the frequency of (or situation requiring) logging for each identified event type];

d. Provide a rationale for why the event types selected for logging are deemed to be adequate to support after-the-fact investigations of incidents; and

e. Review and update the event types selected for logging [frequency].
<<<
COMMENT: Baselines: Low, Moderate, High, Privacy
BASELINE: Low
STATUS: Draft

[REQUIREMENT]
UID: AU-2.1
TITLE: AU-2(1) Compilation of Audit Records from Multiple Sources
STATEMENT: >>>
Withdrawn. Incorporated into AU-12.
<<<
COMMENT: Withdrawn
BASELINE: None
STATUS: Draft

[REQUIREMENT]
UID: AU-2.2
TITLE: AU-2(2) Selection of Audit Events by Component
STATEMENT: >>>
Withdrawn. Incorporated into AU-12.
<<<
COMMENT: Withdrawn
BASELINE: None
STATUS: Draft

[REQUIREMENT]
UID: AU-2.3
TITLE: AU-2(3) Reviews and Updates
STATEMENT: >>>
Withdrawn. Incorporated into AU-2.
<<<
COMMENT: Withdrawn
BASELINE: None
STATUS: Draft

[REQUIREMENT]
UID: AU-2.4
TITLE: AU-2(4) Privileged Functions
STATEMENT: >>>
Withdrawn. Incorporated into AC-6.9.
<<<
COMMENT: Withdrawn
BASELINE: None
STATUS: Draft

[REQUIREMENT]
UID: AU-3
TITLE: AU-3 Content of Audit Records
STATEMENT: >>>
Ensure that audit records contain information that establishes the following:

  a. What type of event occurred;

  b. When the event occurred;

  c. Where the event occurred;

  d. Source of the event;

  e. Outcome of the event; and

  f. Identity of any individuals, subjects, or objects/entities associated with the event.
<<<
COMMENT: Baselines: Low, Moderate, High
BASELINE: Low
STATUS: Draft

[REQUIREMENT]
UID: AU-3.1
TITLE: AU-3(1) Additional Audit Information
STATEMENT: >>>
Generate audit records containing the following additional information: [additional information].
<<<
COMMENT: Baselines: Moderate, High
BASELINE: Moderate
STATUS: Draft

[REQUIREMENT]
UID: AU-3.2
TITLE: AU-3(2) Centralized Management of Planned Audit Record Content
STATEMENT: >>>
Withdrawn. Incorporated into PL-9.
<<<
COMMENT: Withdrawn
BASELINE: None
STATUS: Draft

[REQUIREMENT]
UID: AU-3.3
TITLE: AU-3(3) Limit Personally Identifiable Information Elements
STATEMENT: >>>
Limit personally identifiable information contained in audit records to the following elements identified in the privacy risk assessment: [elements].
<<<
COMMENT: Baselines: Privacy
BASELINE: Privacy
STATUS: Draft

[REQUIREMENT]
UID: AU-4
TITLE: AU-4 Audit Log Storage Capacity
STATEMENT: >>>
Allocate audit log storage capacity to accommodate [audit log retention requirements].
<<<
COMMENT: Baselines: Low, Moderate, High
BASELINE: Low
STATUS: Draft

[REQUIREMENT]
UID: AU-4.1
TITLE: AU-4(1) Transfer to Alternate Storage
STATEMENT: >>>
Transfer audit logs [frequency] to a different system, system component, or media other than the system or system component conducting the logging.
<<<
BASELINE: None
STATUS: Draft

[REQUIREMENT]
UID: AU-5
TITLE: AU-5 Response to Audit Logging Process Failures
STATEMENT: >>>
a. Alert [personnel or roles] within [time period] in the event of an audit logging process failure; and

b. Take the following additional actions: [additional actions].
<<<
COMMENT: Baselines: Low, Moderate, High
BASELINE: Low
STATUS: Draft

[REQUIREMENT]
UID: AU-5.1
TITLE: AU-5(1) Storage Capacity Warning
STATEMENT: >>>
Provide a warning to [personnel, roles, and/or locations] within [time period] when allocated audit log storage volume reaches [percentage] of repository maximum audit log storage capacity.
<<<
COMMENT: Baselines: High
BASELINE: High
STATUS: Draft

[REQUIREMENT]
UID: AU-5.2
TITLE: AU-5(2) Real-time Alerts
STATEMENT: >>>
Provide an alert within [real-time period] to [personnel, roles, and/or locations] when the following audit failure events occur: [audit logging failure events requiring real-time alerts].
<<<
COMMENT: Baselines: High
BASELINE: High
STATUS: Draft

[REQUIREMENT]
UID: AU-5.3
TITLE: AU-5(3) Configurable Traffic Volume Thresholds
STATEMENT: >>>
Enforce configurable network communications traffic volume thresholds reflecting limits on audit log storage capacity and [au-05.03_odp] network traffic above those thresholds.
<<<
BASELINE: None
STATUS: Draft

[REQUIREMENT]
UID: AU-5.4
TITLE: AU-5(4) Shutdown on Failure
STATEMENT: >>>
Invoke a [au-05.04_odp.01] in the event of [audit logging failures] , unless an alternate audit logging capability exists.
<<<
BASELINE: None
STATUS: Draft

[REQUIREMENT]
UID: AU-5.5
TITLE: AU-5(5) Alternate Audit Logging Capability
STATEMENT: >>>
Provide an alternate audit logging capability in the event of a failure in primary audit logging capability that implements [alternate audit logging functionality].
<<<
BASELINE: None
STATUS: Draft

[REQUIREMENT]
UID: AU-6
TITLE: AU-6 Audit Record Review, Analysis, and Reporting
STATEMENT: >>>
a. Review and analyze system audit records [frequency] for indications of [inappropriate or unusual activity] and the potential impact of the inappropriate or unusual activity;

b. Report findings to [personnel or roles] ; and

c. Adjust the level of audit record review, analysis, and reporting within the system when there is a change in risk based on law enforcement information, intelligence information, or other credible sources of information.
<<<
COMMENT: Baselines: Low, Moderate, High
BASELINE: Low
STATUS: Draft

[REQUIREMENT]
UID: AU-6.1
TITLE: AU-6(1) Automated Process Integration
STATEMENT: >>>
Integrate audit record review, analysis, and reporting processes using [automated mechanisms].
<<<
COMMENT: Baselines: Moderate, High
BASELINE: Moderate
STATUS: Draft

[REQUIREMENT]
UID: AU-6.2
TITLE: AU-6(2) Automated Security Alerts
STATEMENT: >>>
Withdrawn. Incorporated into SI-4.
<<<
COMMENT: Withdrawn
BASELINE: None
STATUS: Draft

[REQUIREMENT]
UID: AU-6.3
TITLE: AU-6(3) Correlate Audit Record Repositories
STATEMENT: >>>
Analyze and correlate audit records across different repositories to gain organization-wide situational awareness.
<<<
COMMENT: Baselines: Moderate, High
BASELINE: Moderate
STATUS: Draft

[REQUIREMENT]
UID: AU-6.4
TITLE: AU-6(4) Central Review and Analysis
STATEMENT: >>>
Provide and implement the capability to centrally review and analyze audit records from multiple components within the system.
<<<
BASELINE: None
STATUS: Draft

[REQUIREMENT]
UID: AU-6.5
TITLE: AU-6(5) Integrated Analysis of Audit Records
STATEMENT: >>>
Integrate analysis of audit records with analysis of [au-06.05_odp.01] to further enhance the ability to identify inappropriate or unusual activity.
<<<
COMMENT: Baselines: High
BASELINE: High
STATUS: Draft

[REQUIREMENT]
UID: AU-6.6
TITLE: AU-6(6) Correlation with Physical Monitoring
STATEMENT: >>>
Correlate information from audit records with information obtained from monitoring physical access to further enhance the ability to identify suspicious, inappropriate, unusual, or malevolent activity.
<<<
COMMENT: Baselines: High
BASELINE: High
STATUS: Draft

[REQUIREMENT]
UID: AU-6.7
TITLE: AU-6(7) Permitted Actions
STATEMENT: >>>
Specify the permitted actions for each [au-06.07_odp] associated with the review, analysis, and reporting of audit record information.
<<<
BASELINE: None
STATUS: Draft

[REQUIREMENT]
UID: AU-6.8
TITLE: AU-6(8) Full Text Analysis of Privileged Commands
STATEMENT: >>>
Perform a full text analysis of logged privileged commands in a physically distinct component or subsystem of the system, or other system that is dedicated to that analysis.
<<<
BASELINE: None
STATUS: Draft

[REQUIREMENT]
UID: AU-6.9
TITLE: AU-6(9) Correlation with Information from Nontechnical Sources
STATEMENT: >>>
Correlate information from nontechnical sources with audit record information to enhance organization-wide situational awareness.
<<<
BASELINE: None
STATUS: Draft

[REQUIREMENT]
UID: AU-6.10
TITLE: AU-6(10) Audit Level Adjustment
STATEMENT: >>>
Withdrawn. Incorporated into AU-6.
<<<
COMMENT: Withdrawn
BASELINE: None
STATUS: Draft

[REQUIREMENT]
UID: AU-7
TITLE: AU-7 Audit Record Reduction and Report Generation
STATEMENT: >>>
Provide and implement an audit record reduction and report generation capability that:

  a. Supports on-demand audit record review, analysis, and reporting requirements and after-the-fact investigations of incidents; and

  b. Does not alter the original content or time ordering of audit records.
<<<
COMMENT: Baselines: Moderate, High
BASELINE: Moderate
STATUS: Draft

[REQUIREMENT]
UID: AU-7.1
TITLE: AU-7(1) Automatic Processing
STATEMENT: >>>
Provide and implement the capability to process, sort, and search audit records for events of interest based on the following content: [fields within audit records].
<<<
COMMENT: Baselines: Moderate, High
BASELINE: Moderate
STATUS: Draft

[REQUIREMENT]
UID: AU-7.2
TITLE: AU-7(2) Automatic Sort and Search
STATEMENT: >>>
Withdrawn. Incorporated into AU-7.1.
<<<
COMMENT: Withdrawn
BASELINE: None
STATUS: Draft

[REQUIREMENT]
UID: AU-8
TITLE: AU-8 Time Stamps
STATEMENT: >>>
a. Use internal system clocks to generate time stamps for audit records; and

b. Record time stamps for audit records that meet [granularity of time measurement] and that use Coordinated Universal Time, have a fixed local time offset from Coordinated Universal Time, or that include the local time offset as part of the time stamp.
<<<
COMMENT: Baselines: Low, Moderate, High
BASELINE: Low
STATUS: Draft

[REQUIREMENT]
UID: AU-8.1
TITLE: AU-8(1) Synchronization with Authoritative Time Source
STATEMENT: >>>
Withdrawn.
<<<
COMMENT: Withdrawn
BASELINE: None
STATUS: Draft

[REQUIREMENT]
UID: AU-8.2
TITLE: AU-8(2) Secondary Authoritative Time Source
STATEMENT: >>>
Withdrawn.
<<<
COMMENT: Withdrawn
BASELINE: None
STATUS: Draft

[REQUIREMENT]
UID: AU-9
TITLE: AU-9 Protection of Audit Information
STATEMENT: >>>
a. Protect audit information and audit logging tools from unauthorized access, modification, and deletion; and

b. Alert [personnel or roles] upon detection of unauthorized access, modification, or deletion of audit information.
<<<
COMMENT: Baselines: Low, Moderate, High
BASELINE: Low
STATUS: Draft

[REQUIREMENT]
UID: AU-9.1
TITLE: AU-9(1) Hardware Write-once Media
STATEMENT: >>>
Write audit trails to hardware-enforced, write-once media.
<<<
BASELINE: None
STATUS: Draft

[REQUIREMENT]
UID: AU-9.2
TITLE: AU-9(2) Store on Separate Physical Systems or Components
STATEMENT: >>>
Store audit records [frequency] in a repository that is part of a physically different system or system component than the system or component being audited.
<<<
COMMENT: Baselines: High
BASELINE: High
STATUS: Draft

[REQUIREMENT]
UID: AU-9.3
TITLE: AU-9(3) Cryptographic Protection
STATEMENT: >>>
Implement cryptographic mechanisms to protect the integrity of audit information and audit tools.
<<<
COMMENT: Baselines: High
BASELINE: High
STATUS: Draft

[REQUIREMENT]
UID: AU-9.4
TITLE: AU-9(4) Access by Subset of Privileged Users
STATEMENT: >>>
Authorize access to management of audit logging functionality to only [subset of privileged users or roles].
<<<
COMMENT: Baselines: Moderate, High
BASELINE: Moderate
STATUS: Draft

[REQUIREMENT]
UID: AU-9.5
TITLE: AU-9(5) Dual Authorization
STATEMENT: >>>
Enforce dual authorization for [au-09.05_odp.01] of [audit information].
<<<
BASELINE: None
STATUS: Draft

[REQUIREMENT]
UID: AU-9.6
TITLE: AU-9(6) Read-only Access
STATEMENT: >>>
Authorize read-only access to audit information to [subset of privileged users or roles].
<<<
BASELINE: None
STATUS: Draft

[REQUIREMENT]
UID: AU-9.7
TITLE: AU-9(7) Store on Component with Different Operating System
STATEMENT: >>>
Store audit information on a component running a different operating system than the system or component being audited.
<<<
BASELINE: None
STATUS: Draft

[REQUIREMENT]
UID: AU-10
TITLE: AU-10 Non-repudiation
STATEMENT: >>>
Provide irrefutable evidence that an individual (or process acting on behalf of an individual) has performed [actions].
<<<
COMMENT: Baselines: High
BASELINE: High
STATUS: Draft

[REQUIREMENT]
UID: AU-10.1
TITLE: AU-10(1) Association of Identities
STATEMENT: >>>
(a) Bind the identity of the information producer with the information to [strength of binding] ; and

(b) Provide the means for authorized individuals to determine the identity of the producer of the information.
<<<
BASELINE: None
STATUS: Draft

[REQUIREMENT]
UID: AU-10.2
TITLE: AU-10(2) Validate Binding of Information Producer Identity
STATEMENT: >>>
(a) Validate the binding of the information producer identity to the information at [frequency] ; and

(b) Perform [actions] in the event of a validation error.
<<<
BASELINE: None
STATUS: Draft

[REQUIREMENT]
UID: AU-10.3
TITLE: AU-10(3) Chain of Custody
STATEMENT: >>>
Maintain reviewer or releaser credentials within the established chain of custody for information reviewed or released.
<<<
BASELINE: None
STATUS: Draft

[REQUIREMENT]
UID: AU-10.4
TITLE: AU-10(4) Validate Binding of Information Reviewer Identity
STATEMENT: >>>
(a) Validate the binding of the information reviewer identity to the information at the transfer or release points prior to release or transfer between [security domains] ; and

(b) Perform [actions] in the event of a validation error.
<<<
BASELINE: None
STATUS: Draft

[REQUIREMENT]
UID: AU-10.5
TITLE: AU-10(5) Digital Signatures
STATEMENT: >>>
Withdrawn. Incorporated into SI-7.
<<<
COMMENT: Withdrawn
BASELINE: None
STATUS: Draft

[REQUIREMENT]
UID: AU-11
TITLE: AU-11 Audit Record Retention
STATEMENT: >>>
Retain audit records for [time period] to provide support for after-the-fact investigations of incidents and to meet regulatory and organizational information retention requirements.
<<<
COMMENT: Baselines: Low, Moderate, High, Privacy
BASELINE: Low
STATUS: Draft

[REQUIREMENT]
UID: AU-11.1
TITLE: AU-11(1) Long-term Retrieval Capability
STATEMENT: >>>
Employ [measures] to ensure that long-term audit records generated by the system can be retrieved.
<<<
BASELINE: None
STATUS: Draft

[REQUIREMENT]
UID: AU-12
TITLE: AU-12 Audit Record Generation
STATEMENT: >>>
a. Provide audit record generation capability for the event types the system is capable of auditing as defined in [AU-2a](#au-2_smt.a) on [system components];

b. Allow [personnel or roles] to select the event types that are to be logged by specific components of the system; and

c. Generate audit records for the event types defined in [AU-2c](#au-2_smt.c) that include the audit record content defined in [AU-3](#au-3).
<<<
COMMENT: Baselines: Low, Moderate, High
BASELINE: Low
STATUS: Draft

[REQUIREMENT]
UID: AU-12.1
TITLE: AU-12(1) System-wide and Time-correlated Audit Trail
STATEMENT: >>>
Compile audit records from [system components] into a system-wide (logical or physical) audit trail that is time-correlated to within [level of tolerance].
<<<
COMMENT: Baselines: High
BASELINE: High
STATUS: Draft

[REQUIREMENT]
UID: AU-12.2
TITLE: AU-12(2) Standardized Formats
STATEMENT: >>>
Produce a system-wide (logical or physical) audit trail composed of audit records in a standardized format.
<<<
BASELINE: None
STATUS: Draft

[REQUIREMENT]
UID: AU-12.3
TITLE: AU-12(3) Changes by Authorized Individuals
STATEMENT: >>>
Provide and implement the capability for [individuals or roles] to change the logging to be performed on [system components] based on [selectable event criteria] within [time thresholds].
<<<
COMMENT: Baselines: High
BASELINE: High
STATUS: Draft

[REQUIREMENT]
UID: AU-12.4
TITLE: AU-12(4) Query Parameter Audits of Personally Identifiable Information
STATEMENT: >>>
Provide and implement the capability for auditing the parameters of user query events for data sets containing personally identifiable information.
<<<
BASELINE: None
STATUS: Draft

[REQUIREMENT]
UID: AU-13
TITLE: AU-13 Monitoring for Information Disclosure
STATEMENT: >>>
a. Monitor [open-source information and/or information sites] [frequency] for evidence of unauthorized disclosure of organizational information; and

b. If an information disclosure is discovered:

  1. Notify [personnel or roles] ; and

  2. Take the following additional actions: [additional actions].
<<<
BASELINE: None
STATUS: Draft

[REQUIREMENT]
UID: AU-13.1
TITLE: AU-13(1) Use of Automated Tools
STATEMENT: >>>
Monitor open-source information and information sites using [automated mechanisms].
<<<
BASELINE: None
STATUS: Draft

[REQUIREMENT]
UID: AU-13.2
TITLE: AU-13(2) Review of Monitored Sites
STATEMENT: >>>
Review the list of open-source information sites being monitored [frequency].
<<<
BASELINE: None
STATUS: Draft

[REQUIREMENT]
UID: AU-13.3
TITLE: AU-13(3) Unauthorized Replication of Information
STATEMENT: >>>
Employ discovery techniques, processes, and tools to determine if external entities are replicating organizational information in an unauthorized manner.
<<<
BASELINE: None
STATUS: Draft

[REQUIREMENT]
UID: AU-14
TITLE: AU-14 Session Audit
STATEMENT: >>>
a. Provide and implement the capability for [users or roles] to [au-14_odp.02] the content of a user session under [circumstances] ; and

b. Develop, integrate, and use session auditing activities in consultation with legal counsel and in accordance with applicable laws, executive orders, directives, regulations, policies, standards, and guidelines.
<<<
BASELINE: None
STATUS: Draft

[REQUIREMENT]
UID: AU-14.1
TITLE: AU-14(1) System Start-up
STATEMENT: >>>
Initiate session audits automatically at system start-up.
<<<
BASELINE: None
STATUS: Draft

[REQUIREMENT]
UID: AU-14.2
TITLE: AU-14(2) Capture and Record Content
STATEMENT: >>>
Withdrawn. Incorporated into AU-14.
<<<
COMMENT: Withdrawn
BASELINE: None
STATUS: Draft

[REQUIREMENT]
UID: AU-14.3
TITLE: AU-14(3) Remote Viewing and Listening
STATEMENT: >>>
Provide and implement the capability for authorized users to remotely view and hear content related to an established user session in real time.
<<<
BASELINE: None
STATUS: Draft

[REQUIREMENT]
UID: AU-15
TITLE: AU-15 Alternate Audit Logging Capability
STATEMENT: >>>
Withdrawn.
<<<
COMMENT: Withdrawn
BASELINE: None
STATUS: Draft

[REQUIREMENT]
UID: AU-16
TITLE: AU-16 Cross-organizational Audit Logging
STATEMENT: >>>
Employ [methods] for coordinating [audit information] among external organizations when audit information is transmitted across organizational boundaries.
<<<
BASELINE: None
STATUS: Draft

[REQUIREMENT]
UID: AU-16.1
TITLE: AU-16(1) Identity Preservation
STATEMENT: >>>
Preserve the identity of individuals in cross-organizational audit trails.
<<<
BASELINE: None
STATUS: Draft

[REQUIREMENT]
UID: AU-16.2
TITLE: AU-16(2) Sharing of Audit Information
STATEMENT: >>>
Provide cross-organizational audit information to [organizations] based on [cross-organizational sharing agreements].
<<<
BASELINE: None
STATUS: Draft

[REQUIREMENT]
UID: AU-16.3
TITLE: AU-16(3) Disassociability
STATEMENT: >>>
Implement [measures] to disassociate individuals from audit information transmitted across organizational boundaries.
<<<
BASELINE: None
STATUS: Draft

[[/SECTION]]

[[SECTION]]
UID: NIST-CA
TITLE: CA — Assessment, Authorization, and Monitoring

[REQUIREMENT]
UID: CA-1
TITLE: CA-1 Policy and Procedures
STATEMENT: >>>
a. Develop, document, and disseminate to [organization-defined personnel or roles]:

  1. [ca-01_odp.03] assessment, authorization, and monitoring policy that:

    (a) Addresses purpose, scope, roles, responsibilities, management commitment, coordination among organizational entities, and compliance; and

    (b) Is consistent with applicable laws, executive orders, directives, regulations, policies, standards, and guidelines; and

  2. Procedures to facilitate the implementation of the assessment, authorization, and monitoring policy and the associated assessment, authorization, and monitoring controls;

b. Designate an [official] to manage the development, documentation, and dissemination of the assessment, authorization, and monitoring policy and procedures; and

c. Review and update the current assessment, authorization, and monitoring:

  1. Policy [frequency] and following [events] ; and

  2. Procedures [frequency] and following [events].
<<<
COMMENT: Baselines: Low, Moderate, High, Privacy
BASELINE: Low
STATUS: Draft

[REQUIREMENT]
UID: CA-2
TITLE: CA-2 Control Assessments
STATEMENT: >>>
a. Select the appropriate assessor or assessment team for the type of assessment to be conducted;

b. Develop a control assessment plan that describes the scope of the assessment including:

  1. Controls and control enhancements under assessment;

  2. Assessment procedures to be used to determine control effectiveness; and

  3. Assessment environment, assessment team, and assessment roles and responsibilities;

c. Ensure the control assessment plan is reviewed and approved by the authorizing official or designated representative prior to conducting the assessment;

d. Assess the controls in the system and its environment of operation [assessment frequency] to determine the extent to which the controls are implemented correctly, operating as intended, and producing the desired outcome with respect to meeting established security and privacy requirements;

e. Produce a control assessment report that document the results of the assessment; and

f. Provide the results of the control assessment to [individuals or roles].
<<<
COMMENT: Baselines: Low, Moderate, High, Privacy
BASELINE: Low
STATUS: Draft

[REQUIREMENT]
UID: CA-2.1
TITLE: CA-2(1) Independent Assessors
STATEMENT: >>>
Employ independent assessors or assessment teams to conduct control assessments.
<<<
COMMENT: Baselines: Moderate, High
BASELINE: Moderate
STATUS: Draft

[REQUIREMENT]
UID: CA-2.2
TITLE: CA-2(2) Specialized Assessments
STATEMENT: >>>
Include as part of control assessments, [specialized assessment frequency], [ca-02.02_odp.02], [ca-02.02_odp.03].
<<<
COMMENT: Baselines: High
BASELINE: High
STATUS: Draft

[REQUIREMENT]
UID: CA-2.3
TITLE: CA-2(3) Leveraging Results from External Organizations
STATEMENT: >>>
Leverage the results of control assessments performed by [external organization(s)] on [system] when the assessment meets [requirements].
<<<
BASELINE: None
STATUS: Draft

[REQUIREMENT]
UID: CA-3
TITLE: CA-3 Information Exchange
STATEMENT: >>>
a. Approve and manage the exchange of information between the system and other systems using [ca-03_odp.01];

b. Document, as part of each exchange agreement, the interface characteristics, security and privacy requirements, controls, and responsibilities for each system, and the impact level of the information communicated; and

c. Review and update the agreements [frequency].
<<<
COMMENT: Baselines: Low, Moderate, High
BASELINE: Low
STATUS: Draft

[REQUIREMENT]
UID: CA-3.1
TITLE: CA-3(1) Unclassified National Security System Connections
STATEMENT: >>>
Withdrawn.
<<<
COMMENT: Withdrawn
BASELINE: None
STATUS: Draft

[REQUIREMENT]
UID: CA-3.2
TITLE: CA-3(2) Classified National Security System Connections
STATEMENT: >>>
Withdrawn.
<<<
COMMENT: Withdrawn
BASELINE: None
STATUS: Draft

[REQUIREMENT]
UID: CA-3.3
TITLE: CA-3(3) Unclassified Non-national Security System Connections
STATEMENT: >>>
Withdrawn.
<<<
COMMENT: Withdrawn
BASELINE: None
STATUS: Draft

[REQUIREMENT]
UID: CA-3.4
TITLE: CA-3(4) Connections to Public Networks
STATEMENT: >>>
Withdrawn.
<<<
COMMENT: Withdrawn
BASELINE: None
STATUS: Draft

[REQUIREMENT]
UID: CA-3.5
TITLE: CA-3(5) Restrictions on External System Connections
STATEMENT: >>>
Withdrawn.
<<<
COMMENT: Withdrawn
BASELINE: None
STATUS: Draft

[REQUIREMENT]
UID: CA-3.6
TITLE: CA-3(6) Transfer Authorizations
STATEMENT: >>>
Verify that individuals or systems transferring data between interconnecting systems have the requisite authorizations (i.e., write permissions or privileges) prior to accepting such data.
<<<
COMMENT: Baselines: High
BASELINE: High
STATUS: Draft

[REQUIREMENT]
UID: CA-3.7
TITLE: CA-3(7) Transitive Information Exchanges
STATEMENT: >>>
(a) Identify transitive (downstream) information exchanges with other systems through the systems identified in [CA-3a](#ca-3_smt.a) ; and

(b) Take measures to ensure that transitive (downstream) information exchanges cease when the controls on identified transitive (downstream) systems cannot be verified or validated.
<<<
BASELINE: None
STATUS: Draft

[REQUIREMENT]
UID: CA-4
TITLE: CA-4 Security Certification
STATEMENT: >>>
Withdrawn. Incorporated into CA-2.
<<<
COMMENT: Withdrawn
BASELINE: None
STATUS: Draft

[REQUIREMENT]
UID: CA-5
TITLE: CA-5 Plan of Action and Milestones
STATEMENT: >>>
a. Develop a plan of action and milestones for the system to document the planned remediation actions of the organization to correct weaknesses or deficiencies noted during the assessment of the controls and to reduce or eliminate known vulnerabilities in the system; and

b. Update existing plan of action and milestones [frequency] based on the findings from control assessments, independent audits or reviews, and continuous monitoring activities.
<<<
COMMENT: Baselines: Low, Moderate, High, Privacy
BASELINE: Low
STATUS: Draft

[REQUIREMENT]
UID: CA-5.1
TITLE: CA-5(1) Automation Support for Accuracy and Currency
STATEMENT: >>>
Ensure the accuracy, currency, and availability of the plan of action and milestones for the system using [automated mechanisms].
<<<
BASELINE: None
STATUS: Draft

[REQUIREMENT]
UID: CA-6
TITLE: CA-6 Authorization
STATEMENT: >>>
a. Assign a senior official as the authorizing official for the system;

b. Assign a senior official as the authorizing official for common controls available for inheritance by organizational systems;

c. Ensure that the authorizing official for the system, before commencing operations:

  1. Accepts the use of common controls inherited by the system; and

  2. Authorizes the system to operate;

d. Ensure that the authorizing official for common controls authorizes the use of those controls for inheritance by organizational systems;

e. Update the authorizations [frequency].
<<<
COMMENT: Baselines: Low, Moderate, High, Privacy
BASELINE: Low
STATUS: Draft

[REQUIREMENT]
UID: CA-6.1
TITLE: CA-6(1) Joint Authorization — Intra-organization
STATEMENT: >>>
Employ a joint authorization process for the system that includes multiple authorizing officials from the same organization conducting the authorization.
<<<
BASELINE: None
STATUS: Draft

[REQUIREMENT]
UID: CA-6.2
TITLE: CA-6(2) Joint Authorization — Inter-organization
STATEMENT: >>>
Employ a joint authorization process for the system that includes multiple authorizing officials with at least one authorizing official from an organization external to the organization conducting the authorization.
<<<
BASELINE: None
STATUS: Draft

[REQUIREMENT]
UID: CA-7
TITLE: CA-7 Continuous Monitoring
STATEMENT: >>>
Develop a system-level continuous monitoring strategy and implement continuous monitoring in accordance with the organization-level continuous monitoring strategy that includes:

  a. Establishing the following system-level metrics to be monitored: [system-level metrics];

  b. Establishing [frequencies] for monitoring and [frequencies] for assessment of control effectiveness;

  c. Ongoing control assessments in accordance with the continuous monitoring strategy;

  d. Ongoing monitoring of system and organization-defined metrics in accordance with the continuous monitoring strategy;

  e. Correlation and analysis of information generated by control assessments and monitoring;

  f. Response actions to address results of the analysis of control assessment and monitoring information; and

  g. Reporting the security and privacy status of the system to [organization-defined personnel or roles] [organization-defined frequency].
<<<
COMMENT: Baselines: Low, Moderate, High, Privacy
BASELINE: Low
STATUS: Draft

[REQUIREMENT]
UID: CA-7.1
TITLE: CA-7(1) Independent Assessment
STATEMENT: >>>
Employ independent assessors or assessment teams to monitor the controls in the system on an ongoing basis.
<<<
COMMENT: Baselines: Moderate, High
BASELINE: Moderate
STATUS: Draft

[REQUIREMENT]
UID: CA-7.2
TITLE: CA-7(2) Types of Assessments
STATEMENT: >>>
Withdrawn. Incorporated into CA-2.
<<<
COMMENT: Withdrawn
BASELINE: None
STATUS: Draft

[REQUIREMENT]
UID: CA-7.3
TITLE: CA-7(3) Trend Analyses
STATEMENT: >>>
Employ trend analyses to determine if control implementations, the frequency of continuous monitoring activities, and the types of activities used in the continuous monitoring process need to be modified based on empirical data.
<<<
BASELINE: None
STATUS: Draft

[REQUIREMENT]
UID: CA-7.4
TITLE: CA-7(4) Risk Monitoring
STATEMENT: >>>
Ensure risk monitoring is an integral part of the continuous monitoring strategy that includes the following:

  (a) Effectiveness monitoring;

  (b) Compliance monitoring; and

  (c) Change monitoring.
<<<
COMMENT: Baselines: Low, Moderate, High, Privacy
BASELINE: Low
STATUS: Draft

[REQUIREMENT]
UID: CA-7.5
TITLE: CA-7(5) Consistency Analysis
STATEMENT: >>>
Employ the following actions to validate that policies are established and implemented controls are operating in a consistent manner: [organization-defined actions].
<<<
BASELINE: None
STATUS: Draft

[REQUIREMENT]
UID: CA-7.6
TITLE: CA-7(6) Automation Support for Monitoring
STATEMENT: >>>
Ensure the accuracy, currency, and availability of monitoring results for the system using [automated mechanisms].
<<<
BASELINE: None
STATUS: Draft

[REQUIREMENT]
UID: CA-8
TITLE: CA-8 Penetration Testing
STATEMENT: >>>
Conduct penetration testing [frequency] on [system(s) or system components].
<<<
COMMENT: Baselines: High
BASELINE: High
STATUS: Draft

[REQUIREMENT]
UID: CA-8.1
TITLE: CA-8(1) Independent Penetration Testing Agent or Team
STATEMENT: >>>
Employ an independent penetration testing agent or team to perform penetration testing on the system or system components.
<<<
COMMENT: Baselines: High
BASELINE: High
STATUS: Draft

[REQUIREMENT]
UID: CA-8.2
TITLE: CA-8(2) Red Team Exercises
STATEMENT: >>>
Employ the following red-team exercises to simulate attempts by adversaries to compromise organizational systems in accordance with applicable rules of engagement: [red team exercises].
<<<
BASELINE: None
STATUS: Draft

[REQUIREMENT]
UID: CA-8.3
TITLE: CA-8(3) Facility Penetration Testing
STATEMENT: >>>
Employ a penetration testing process that includes [frequency] [ca-08.03_odp.02] attempts to bypass or circumvent controls associated with physical access points to the facility.
<<<
BASELINE: None
STATUS: Draft

[REQUIREMENT]
UID: CA-9
TITLE: CA-9 Internal System Connections
STATEMENT: >>>
a. Authorize internal connections of [system components] to the system;

b. Document, for each internal connection, the interface characteristics, security and privacy requirements, and the nature of the information communicated;

c. Terminate internal system connections after [conditions] ; and

d. Review [frequency] the continued need for each internal connection.
<<<
COMMENT: Baselines: Low, Moderate, High
BASELINE: Low
STATUS: Draft

[REQUIREMENT]
UID: CA-9.1
TITLE: CA-9(1) Compliance Checks
STATEMENT: >>>
Perform security and privacy compliance checks on constituent system components prior to the establishment of the internal connection.
<<<
BASELINE: None
STATUS: Draft

[[/SECTION]]

[[SECTION]]
UID: NIST-CM
TITLE: CM — Configuration Management

[REQUIREMENT]
UID: CM-1
TITLE: CM-1 Policy and Procedures
STATEMENT: >>>
a. Develop, document, and disseminate to [organization-defined personnel or roles]:

  1. [cm-01_odp.03] configuration management policy that:

    (a) Addresses purpose, scope, roles, responsibilities, management commitment, coordination among organizational entities, and compliance; and

    (b) Is consistent with applicable laws, executive orders, directives, regulations, policies, standards, and guidelines; and

  2. Procedures to facilitate the implementation of the configuration management policy and the associated configuration management controls;

b. Designate an [official] to manage the development, documentation, and dissemination of the configuration management policy and procedures; and

c. Review and update the current configuration management:

  1. Policy [frequency] and following [events] ; and

  2. Procedures [frequency] and following [events].
<<<
COMMENT: Baselines: Low, Moderate, High, Privacy
BASELINE: Low
STATUS: Draft

[REQUIREMENT]
UID: CM-2
TITLE: CM-2 Baseline Configuration
STATEMENT: >>>
a. Develop, document, and maintain under configuration control, a current baseline configuration of the system; and

b. Review and update the baseline configuration of the system:

  1. [frequency];

  2. When required due to [circumstances] ; and

  3. When system components are installed or upgraded.
<<<
COMMENT: Baselines: Low, Moderate, High
BASELINE: Low
STATUS: Draft

[REQUIREMENT]
UID: CM-2.1
TITLE: CM-2(1) Reviews and Updates
STATEMENT: >>>
Withdrawn. Incorporated into CM-2.
<<<
COMMENT: Withdrawn
BASELINE: None
STATUS: Draft

[REQUIREMENT]
UID: CM-2.2
TITLE: CM-2(2) Automation Support for Accuracy and Currency
STATEMENT: >>>
Maintain the currency, completeness, accuracy, and availability of the baseline configuration of the system using [automated mechanisms].
<<<
COMMENT: Baselines: Moderate, High
BASELINE: Moderate
STATUS: Draft

[REQUIREMENT]
UID: CM-2.3
TITLE: CM-2(3) Retention of Previous Configurations
STATEMENT: >>>
Retain [number] of previous versions of baseline configurations of the system to support rollback.
<<<
COMMENT: Baselines: Moderate, High
BASELINE: Moderate
STATUS: Draft

[REQUIREMENT]
UID: CM-2.4
TITLE: CM-2(4) Unauthorized Software
STATEMENT: >>>
Withdrawn. Incorporated into CM-7.4.
<<<
COMMENT: Withdrawn
BASELINE: None
STATUS: Draft

[REQUIREMENT]
UID: CM-2.5
TITLE: CM-2(5) Authorized Software
STATEMENT: >>>
Withdrawn. Incorporated into CM-7.5.
<<<
COMMENT: Withdrawn
BASELINE: None
STATUS: Draft

[REQUIREMENT]
UID: CM-2.6
TITLE: CM-2(6) Development and Test Environments
STATEMENT: >>>
Maintain a baseline configuration for system development and test environments that is managed separately from the operational baseline configuration.
<<<
BASELINE: None
STATUS: Draft

[REQUIREMENT]
UID: CM-2.7
TITLE: CM-2(7) Configure Systems and Components for High-risk Areas
STATEMENT: >>>
(a) Issue [systems or system components] with [configurations] to individuals traveling to locations that the organization deems to be of significant risk; and

(b) Apply the following controls to the systems or components when the individuals return from travel: [controls].
<<<
COMMENT: Baselines: Moderate, High
BASELINE: Moderate
STATUS: Draft

[REQUIREMENT]
UID: CM-3
TITLE: CM-3 Configuration Change Control
STATEMENT: >>>
a. Determine and document the types of changes to the system that are configuration-controlled;

b. Review proposed configuration-controlled changes to the system and approve or disapprove such changes with explicit consideration for security and privacy impact analyses;

c. Document configuration change decisions associated with the system;

d. Implement approved configuration-controlled changes to the system;

e. Retain records of configuration-controlled changes to the system for [time period];

f. Monitor and review activities associated with configuration-controlled changes to the system; and

g. Coordinate and provide oversight for configuration change control activities through [configuration change control element] that convenes [cm-03_odp.03].
<<<
COMMENT: Baselines: Moderate, High
BASELINE: Moderate
STATUS: Draft

[REQUIREMENT]
UID: CM-3.1
TITLE: CM-3(1) Automated Documentation, Notification, and Prohibition of Changes
STATEMENT: >>>
Use [automated mechanisms] to:

  (a) Document proposed changes to the system;

  (b) Notify [approval authorities] of proposed changes to the system and request change approval;

  (c) Highlight proposed changes to the system that have not been approved or disapproved within [time period];

  (d) Prohibit changes to the system until designated approvals are received;

  (e) Document all changes to the system; and

  (f) Notify [personnel] when approved changes to the system are completed.
<<<
COMMENT: Baselines: High
BASELINE: High
STATUS: Draft

[REQUIREMENT]
UID: CM-3.2
TITLE: CM-3(2) Testing, Validation, and Documentation of Changes
STATEMENT: >>>
Test, validate, and document changes to the system before finalizing the implementation of the changes.
<<<
COMMENT: Baselines: Moderate, High
BASELINE: Moderate
STATUS: Draft

[REQUIREMENT]
UID: CM-3.3
TITLE: CM-3(3) Automated Change Implementation
STATEMENT: >>>
Implement changes to the current system baseline and deploy the updated baseline across the installed base using [automated mechanisms].
<<<
BASELINE: None
STATUS: Draft

[REQUIREMENT]
UID: CM-3.4
TITLE: CM-3(4) Security and Privacy Representatives
STATEMENT: >>>
Require [organization-defined security and privacy representatives] to be members of the [configuration change control element].
<<<
COMMENT: Baselines: Moderate, High
BASELINE: Moderate
STATUS: Draft

[REQUIREMENT]
UID: CM-3.5
TITLE: CM-3(5) Automated Security Response
STATEMENT: >>>
Implement the following security responses automatically if baseline configurations are changed in an unauthorized manner: [security responses].
<<<
BASELINE: None
STATUS: Draft

[REQUIREMENT]
UID: CM-3.6
TITLE: CM-3(6) Cryptography Management
STATEMENT: >>>
Ensure that cryptographic mechanisms used to provide the following controls are under configuration management: [controls].
<<<
COMMENT: Baselines: High
BASELINE: High
STATUS: Draft

[REQUIREMENT]
UID: CM-3.7
TITLE: CM-3(7) Review System Changes
STATEMENT: >>>
Review changes to the system [frequency] or when [circumstances] to determine whether unauthorized changes have occurred.
<<<
BASELINE: None
STATUS: Draft

[REQUIREMENT]
UID: CM-3.8
TITLE: CM-3(8) Prevent or Restrict Configuration Changes
STATEMENT: >>>
Prevent or restrict changes to the configuration of the system under the following circumstances: [circumstances].
<<<
BASELINE: None
STATUS: Draft

[REQUIREMENT]
UID: CM-4
TITLE: CM-4 Impact Analyses
STATEMENT: >>>
Analyze changes to the system to determine potential security and privacy impacts prior to change implementation.
<<<
COMMENT: Baselines: Low, Moderate, High, Privacy
BASELINE: Low
STATUS: Draft

[REQUIREMENT]
UID: CM-4.1
TITLE: CM-4(1) Separate Test Environments
STATEMENT: >>>
Analyze changes to the system in a separate test environment before implementation in an operational environment, looking for security and privacy impacts due to flaws, weaknesses, incompatibility, or intentional malice.
<<<
COMMENT: Baselines: High
BASELINE: High
STATUS: Draft

[REQUIREMENT]
UID: CM-4.2
TITLE: CM-4(2) Verification of Controls
STATEMENT: >>>
After system changes, verify that the impacted controls are implemented correctly, operating as intended, and producing the desired outcome with regard to meeting the security and privacy requirements for the system.
<<<
COMMENT: Baselines: Moderate, High
BASELINE: Moderate
STATUS: Draft

[REQUIREMENT]
UID: CM-5
TITLE: CM-5 Access Restrictions for Change
STATEMENT: >>>
Define, document, approve, and enforce physical and logical access restrictions associated with changes to the system.
<<<
COMMENT: Baselines: Low, Moderate, High
BASELINE: Low
STATUS: Draft

[REQUIREMENT]
UID: CM-5.1
TITLE: CM-5(1) Automated Access Enforcement and Audit Records
STATEMENT: >>>
(a) Enforce access restrictions using [automated mechanisms] ; and

(b) Automatically generate audit records of the enforcement actions.
<<<
COMMENT: Baselines: High
BASELINE: High
STATUS: Draft

[REQUIREMENT]
UID: CM-5.2
TITLE: CM-5(2) Review System Changes
STATEMENT: >>>
Withdrawn. Incorporated into CM-3.7.
<<<
COMMENT: Withdrawn
BASELINE: None
STATUS: Draft

[REQUIREMENT]
UID: CM-5.3
TITLE: CM-5(3) Signed Components
STATEMENT: >>>
Withdrawn.
<<<
COMMENT: Withdrawn
BASELINE: None
STATUS: Draft

[REQUIREMENT]
UID: CM-5.4
TITLE: CM-5(4) Dual Authorization
STATEMENT: >>>
Enforce dual authorization for implementing changes to [organization-defined system components and system-level information].
<<<
BASELINE: None
STATUS: Draft

[REQUIREMENT]
UID: CM-5.5
TITLE: CM-5(5) Privilege Limitation for Production and Operation
STATEMENT: >>>
(a) Limit privileges to change system components and system-related information within a production or operational environment; and

(b) Review and reevaluate privileges [organization-defined frequency].
<<<
BASELINE: None
STATUS: Draft

[REQUIREMENT]
UID: CM-5.6
TITLE: CM-5(6) Limit Library Privileges
STATEMENT: >>>
Limit privileges to change software resident within software libraries.
<<<
BASELINE: None
STATUS: Draft

[REQUIREMENT]
UID: CM-5.7
TITLE: CM-5(7) Automatic Implementation of Security Safeguards
STATEMENT: >>>
Withdrawn. Incorporated into SI-7.
<<<
COMMENT: Withdrawn
BASELINE: None
STATUS: Draft

[REQUIREMENT]
UID: CM-6
TITLE: CM-6 Configuration Settings
STATEMENT: >>>
a. Establish and document configuration settings for components employed within the system that reflect the most restrictive mode consistent with operational requirements using [common secure configurations];

b. Implement the configuration settings;

c. Identify, document, and approve any deviations from established configuration settings for [system components] based on [operational requirements] ; and

d. Monitor and control changes to the configuration settings in accordance with organizational policies and procedures.
<<<
COMMENT: Baselines: Low, Moderate, High
BASELINE: Low
STATUS: Draft

[REQUIREMENT]
UID: CM-6.1
TITLE: CM-6(1) Automated Management, Application, and Verification
STATEMENT: >>>
Manage, apply, and verify configuration settings for [system components] using [organization-defined automated mechanisms].
<<<
COMMENT: Baselines: High
BASELINE: High
STATUS: Draft

[REQUIREMENT]
UID: CM-6.2
TITLE: CM-6(2) Respond to Unauthorized Changes
STATEMENT: >>>
Take the following actions in response to unauthorized changes to [configuration settings]: [actions].
<<<
COMMENT: Baselines: High
BASELINE: High
STATUS: Draft

[REQUIREMENT]
UID: CM-6.3
TITLE: CM-6(3) Unauthorized Change Detection
STATEMENT: >>>
Withdrawn. Incorporated into SI-7.
<<<
COMMENT: Withdrawn
BASELINE: None
STATUS: Draft

[REQUIREMENT]
UID: CM-6.4
TITLE: CM-6(4) Conformance Demonstration
STATEMENT: >>>
Withdrawn. Incorporated into CM-4.
<<<
COMMENT: Withdrawn
BASELINE: None
STATUS: Draft

[REQUIREMENT]
UID: CM-7
TITLE: CM-7 Least Functionality
STATEMENT: >>>
a. Configure the system to provide only [mission-essential capabilities] ; and

b. Prohibit or restrict the use of the following functions, ports, protocols, software, and/or services: [organization-defined prohibited or restricted functions, system ports, protocols, software, and/or services].
<<<
COMMENT: Baselines: Low, Moderate, High
BASELINE: Low
STATUS: Draft

[REQUIREMENT]
UID: CM-7.1
TITLE: CM-7(1) Periodic Review
STATEMENT: >>>
(a) Review the system [frequency] to identify unnecessary and/or nonsecure functions, ports, protocols, software, and services; and

(b) Disable or remove [organization-defined functions, ports, protocols, software, and services within the system deemed to be unnecessary and/or nonsecure].
<<<
COMMENT: Baselines: Moderate, High
BASELINE: Moderate
STATUS: Draft

[REQUIREMENT]
UID: CM-7.2
TITLE: CM-7(2) Prevent Program Execution
STATEMENT: >>>
Prevent program execution in accordance with [cm-07.02_odp.01].
<<<
COMMENT: Baselines: Moderate, High
BASELINE: Moderate
STATUS: Draft

[REQUIREMENT]
UID: CM-7.3
TITLE: CM-7(3) Registration Compliance
STATEMENT: >>>
Ensure compliance with [registration requirements].
<<<
BASELINE: None
STATUS: Draft

[REQUIREMENT]
UID: CM-7.4
TITLE: CM-7(4) Unauthorized Software — Deny-by-exception
STATEMENT: >>>
(a) Identify [software programs];

(b) Employ an allow-all, deny-by-exception policy to prohibit the execution of unauthorized software programs on the system; and

(c) Review and update the list of unauthorized software programs [frequency].
<<<
BASELINE: None
STATUS: Draft

[REQUIREMENT]
UID: CM-7.5
TITLE: CM-7(5) Authorized Software — Allow-by-exception
STATEMENT: >>>
(a) Identify [software programs];

(b) Employ a deny-all, permit-by-exception policy to allow the execution of authorized software programs on the system; and

(c) Review and update the list of authorized software programs [frequency].
<<<
COMMENT: Baselines: Moderate, High
BASELINE: Moderate
STATUS: Draft

[REQUIREMENT]
UID: CM-7.6
TITLE: CM-7(6) Confined Environments with Limited Privileges
STATEMENT: >>>
Require that the following user-installed software execute in a confined physical or virtual machine environment with limited privileges: [user-installed software].
<<<
BASELINE: None
STATUS: Draft

[REQUIREMENT]
UID: CM-7.7
TITLE: CM-7(7) Code Execution in Protected Environments
STATEMENT: >>>
Allow execution of binary or machine-executable code only in confined physical or virtual machine environments and with the explicit approval of [personnel or roles] when such code is:

  (a) Obtained from sources with limited or no warranty; and/or

  (b) Without the provision of source code.
<<<
BASELINE: None
STATUS: Draft

[REQUIREMENT]
UID: CM-7.8
TITLE: CM-7(8) Binary or Machine Executable Code
STATEMENT: >>>
(a) Prohibit the use of binary or machine-executable code from sources with limited or no warranty or without the provision of source code; and

(b) Allow exceptions only for compelling mission or operational requirements and with the approval of the authorizing official.
<<<
BASELINE: None
STATUS: Draft

[REQUIREMENT]
UID: CM-7.9
TITLE: CM-7(9) Prohibiting The Use of Unauthorized Hardware
STATEMENT: >>>
(a) Identify [hardware components];

(b) Prohibit the use or connection of unauthorized hardware components;

(c) Review and update the list of authorized hardware components [frequency].
<<<
BASELINE: None
STATUS: Draft

[REQUIREMENT]
UID: CM-8
TITLE: CM-8 System Component Inventory
STATEMENT: >>>
a. Develop and document an inventory of system components that:

  1. Accurately reflects the system;

  2. Includes all components within the system;

  3. Does not include duplicate accounting of components or components assigned to any other system;

  4. Is at the level of granularity deemed necessary for tracking and reporting; and

  5. Includes the following information to achieve system component accountability: [information] ; and

b. Review and update the system component inventory [frequency].
<<<
COMMENT: Baselines: Low, Moderate, High
BASELINE: Low
STATUS: Draft

[REQUIREMENT]
UID: CM-8.1
TITLE: CM-8(1) Updates During Installation and Removal
STATEMENT: >>>
Update the inventory of system components as part of component installations, removals, and system updates.
<<<
COMMENT: Baselines: Moderate, High
BASELINE: Moderate
STATUS: Draft

[REQUIREMENT]
UID: CM-8.2
TITLE: CM-8(2) Automated Maintenance
STATEMENT: >>>
Maintain the currency, completeness, accuracy, and availability of the inventory of system components using [organization-defined automated mechanisms].
<<<
COMMENT: Baselines: High
BASELINE: High
STATUS: Draft

[REQUIREMENT]
UID: CM-8.3
TITLE: CM-8(3) Automated Unauthorized Component Detection
STATEMENT: >>>
(a) Detect the presence of unauthorized hardware, software, and firmware components within the system using [organization-defined automated mechanisms] [frequency] ; and

(b) Take the following actions when unauthorized components are detected: [cm-08.03_odp.05].
<<<
COMMENT: Baselines: Moderate, High
BASELINE: Moderate
STATUS: Draft

[REQUIREMENT]
UID: CM-8.4
TITLE: CM-8(4) Accountability Information
STATEMENT: >>>
Include in the system component inventory information, a means for identifying by [cm-08.04_odp] , individuals responsible and accountable for administering those components.
<<<
COMMENT: Baselines: High
BASELINE: High
STATUS: Draft

[REQUIREMENT]
UID: CM-8.5
TITLE: CM-8(5) No Duplicate Accounting of Components
STATEMENT: >>>
Withdrawn. Incorporated into CM-8.
<<<
COMMENT: Withdrawn
BASELINE: None
STATUS: Draft

[REQUIREMENT]
UID: CM-8.6
TITLE: CM-8(6) Assessed Configurations and Approved Deviations
STATEMENT: >>>
Include assessed component configurations and any approved deviations to current deployed configurations in the system component inventory.
<<<
BASELINE: None
STATUS: Draft

[REQUIREMENT]
UID: CM-8.7
TITLE: CM-8(7) Centralized Repository
STATEMENT: >>>
Provide a centralized repository for the inventory of system components.
<<<
BASELINE: None
STATUS: Draft

[REQUIREMENT]
UID: CM-8.8
TITLE: CM-8(8) Automated Location Tracking
STATEMENT: >>>
Support the tracking of system components by geographic location using [automated mechanisms].
<<<
BASELINE: None
STATUS: Draft

[REQUIREMENT]
UID: CM-8.9
TITLE: CM-8(9) Assignment of Components to Systems
STATEMENT: >>>
(a) Assign system components to a system; and

(b) Receive an acknowledgement from [personnel or roles] of this assignment.
<<<
BASELINE: None
STATUS: Draft

[REQUIREMENT]
UID: CM-9
TITLE: CM-9 Configuration Management Plan
STATEMENT: >>>
Develop, document, and implement a configuration management plan for the system that:

  a. Addresses roles, responsibilities, and configuration management processes and procedures;

  b. Establishes a process for identifying configuration items throughout the system development life cycle and for managing the configuration of the configuration items;

  c. Defines the configuration items for the system and places the configuration items under configuration management;

  d. Is reviewed and approved by [personnel or roles] ; and

  e. Protects the configuration management plan from unauthorized disclosure and modification.
<<<
COMMENT: Baselines: Moderate, High
BASELINE: Moderate
STATUS: Draft

[REQUIREMENT]
UID: CM-9.1
TITLE: CM-9(1) Assignment of Responsibility
STATEMENT: >>>
Assign responsibility for developing the configuration management process to organizational personnel that are not directly involved in system development.
<<<
BASELINE: None
STATUS: Draft

[REQUIREMENT]
UID: CM-10
TITLE: CM-10 Software Usage Restrictions
STATEMENT: >>>
a. Use software and associated documentation in accordance with contract agreements and copyright laws;

b. Track the use of software and associated documentation protected by quantity licenses to control copying and distribution; and

c. Control and document the use of peer-to-peer file sharing technology to ensure that this capability is not used for the unauthorized distribution, display, performance, or reproduction of copyrighted work.
<<<
COMMENT: Baselines: Low, Moderate, High
BASELINE: Low
STATUS: Draft

[REQUIREMENT]
UID: CM-10.1
TITLE: CM-10(1) Open-source Software
STATEMENT: >>>
Establish the following restrictions on the use of open-source software: [restrictions].
<<<
BASELINE: None
STATUS: Draft

[REQUIREMENT]
UID: CM-11
TITLE: CM-11 User-installed Software
STATEMENT: >>>
a. Establish [policies] governing the installation of software by users;

b. Enforce software installation policies through the following methods: [methods] ; and

c. Monitor policy compliance [frequency].
<<<
COMMENT: Baselines: Low, Moderate, High
BASELINE: Low
STATUS: Draft

[REQUIREMENT]
UID: CM-11.1
TITLE: CM-11(1) Alerts for Unauthorized Installations
STATEMENT: >>>
Withdrawn. Incorporated into CM-8.3.
<<<
COMMENT: Withdrawn
BASELINE: None
STATUS: Draft

[REQUIREMENT]
UID: CM-11.2
TITLE: CM-11(2) Software Installation with Privileged Status
STATEMENT: >>>
Allow user installation of software only with explicit privileged status.
<<<
BASELINE: None
STATUS: Draft

[REQUIREMENT]
UID: CM-11.3
TITLE: CM-11(3) Automated Enforcement and Monitoring
STATEMENT: >>>
Enforce and monitor compliance with software installation policies using [organization-defined automated mechanisms].
<<<
BASELINE: None
STATUS: Draft

[REQUIREMENT]
UID: CM-12
TITLE: CM-12 Information Location
STATEMENT: >>>
a. Identify and document the location of [information] and the specific system components on which the information is processed and stored;

b. Identify and document the users who have access to the system and system components where the information is processed and stored; and

c. Document changes to the location (i.e., system or system components) where the information is processed and stored.
<<<
COMMENT: Baselines: Moderate, High
BASELINE: Moderate
STATUS: Draft

[REQUIREMENT]
UID: CM-12.1
TITLE: CM-12(1) Automated Tools to Support Information Location
STATEMENT: >>>
Use automated tools to identify [information by information type] on [system components] to ensure controls are in place to protect organizational information and individual privacy.
<<<
COMMENT: Baselines: Moderate, High
BASELINE: Moderate
STATUS: Draft

[REQUIREMENT]
UID: CM-13
TITLE: CM-13 Data Action Mapping
STATEMENT: >>>
Develop and document a map of system data actions.
<<<
BASELINE: None
STATUS: Draft

[REQUIREMENT]
UID: CM-14
TITLE: CM-14 Signed Components
STATEMENT: >>>
Prevent the installation of [organization-defined software and firmware components] without verification that the component has been digitally signed using a certificate that is recognized and approved by the organization.
<<<
BASELINE: None
STATUS: Draft

[[/SECTION]]

[[SECTION]]
UID: NIST-CP
TITLE: CP — Contingency Planning

[REQUIREMENT]
UID: CP-1
TITLE: CP-1 Policy and Procedures
STATEMENT: >>>
a. Develop, document, and disseminate to [organization-defined personnel or roles]:

  1. [cp-01_odp.03] contingency planning policy that:

    (a) Addresses purpose, scope, roles, responsibilities, management commitment, coordination among organizational entities, and compliance; and

    (b) Is consistent with applicable laws, executive orders, directives, regulations, policies, standards, and guidelines; and

  2. Procedures to facilitate the implementation of the contingency planning policy and the associated contingency planning controls;

b. Designate an [official] to manage the development, documentation, and dissemination of the contingency planning policy and procedures; and

c. Review and update the current contingency planning:

  1. Policy [frequency] and following [events] ; and

  2. Procedures [frequency] and following [events].
<<<
COMMENT: Baselines: Low, Moderate, High
BASELINE: Low
STATUS: Draft

[REQUIREMENT]
UID: CP-2
TITLE: CP-2 Contingency Plan
STATEMENT: >>>
a. Develop a contingency plan for the system that:

  1. Identifies essential mission and business functions and associated contingency requirements;

  2. Provides recovery objectives, restoration priorities, and metrics;

  3. Addresses contingency roles, responsibilities, assigned individuals with contact information;

  4. Addresses maintaining essential mission and business functions despite a system disruption, compromise, or failure;

  5. Addresses eventual, full system restoration without deterioration of the controls originally planned and implemented;

  6. Addresses the sharing of contingency information; and

  7. Is reviewed and approved by [organization-defined personnel or roles];

b. Distribute copies of the contingency plan to [organization-defined key contingency personnel (identified by name and/or by role) and organizational elements];

c. Coordinate contingency planning activities with incident handling activities;

d. Review the contingency plan for the system [frequency];

e. Update the contingency plan to address changes to the organization, system, or environment of operation and problems encountered during contingency plan implementation, execution, or testing;

f. Communicate contingency plan changes to [organization-defined key contingency personnel (identified by name and/or by role) and organizational elements];

g. Incorporate lessons learned from contingency plan testing, training, or actual contingency activities into contingency testing and training; and

h. Protect the contingency plan from unauthorized disclosure and modification.
<<<
COMMENT: Baselines: Low, Moderate, High
BASELINE: Low
STATUS: Draft

[REQUIREMENT]
UID: CP-2.1
TITLE: CP-2(1) Coordinate with Related Plans
STATEMENT: >>>
Coordinate contingency plan development with organizational elements responsible for related plans.
<<<
COMMENT: Baselines: Moderate, High
BASELINE: Moderate
STATUS: Draft

[REQUIREMENT]
UID: CP-2.2
TITLE: CP-2(2) Capacity Planning
STATEMENT: >>>
Conduct capacity planning so that necessary capacity for information processing, telecommunications, and environmental support exists during contingency operations.
<<<
COMMENT: Baselines: High
BASELINE: High
STATUS: Draft

[REQUIREMENT]
UID: CP-2.3
TITLE: CP-2(3) Resume Mission and Business Functions
STATEMENT: >>>
Plan for the resumption of [cp-02.03_odp.01] mission and business functions within [time period] of contingency plan activation.
<<<
COMMENT: Baselines: Moderate, High
BASELINE: Moderate
STATUS: Draft

[REQUIREMENT]
UID: CP-2.4
TITLE: CP-2(4) Resume All Mission and Business Functions
STATEMENT: >>>
Withdrawn. Incorporated into CP-2.3.
<<<
COMMENT: Withdrawn
BASELINE: None
STATUS: Draft

[REQUIREMENT]
UID: CP-2.5
TITLE: CP-2(5) Continue Mission and Business Functions
STATEMENT: >>>
Plan for the continuance of [cp-02.05_odp] mission and business functions with minimal or no loss of operational continuity and sustains that continuity until full system restoration at primary processing and/or storage sites.
<<<
COMMENT: Baselines: High
BASELINE: High
STATUS: Draft

[REQUIREMENT]
UID: CP-2.6
TITLE: CP-2(6) Alternate Processing and Storage Sites
STATEMENT: >>>
Plan for the transfer of [cp-02.06_odp] mission and business functions to alternate processing and/or storage sites with minimal or no loss of operational continuity and sustain that continuity through system restoration to primary processing and/or storage sites.
<<<
BASELINE: None
STATUS: Draft

[REQUIREMENT]
UID: CP-2.7
TITLE: CP-2(7) Coordinate with External Service Providers
STATEMENT: >>>
Coordinate the contingency plan with the contingency plans of external service providers to ensure that contingency requirements can be satisfied.
<<<
BASELINE: None
STATUS: Draft

[REQUIREMENT]
UID: CP-2.8
TITLE: CP-2(8) Identify Critical Assets
STATEMENT: >>>
Identify critical system assets supporting [cp-02.08_odp] mission and business functions.
<<<
COMMENT: Baselines: Moderate, High
BASELINE: Moderate
STATUS: Draft

[REQUIREMENT]
UID: CP-3
TITLE: CP-3 Contingency Training
STATEMENT: >>>
a. Provide contingency training to system users consistent with assigned roles and responsibilities:

  1. Within [time period] of assuming a contingency role or responsibility;

  2. When required by system changes; and

  3. [frequency] thereafter; and

b. Review and update contingency training content [frequency] and following [events].
<<<
COMMENT: Baselines: Low, Moderate, High
BASELINE: Low
STATUS: Draft

[REQUIREMENT]
UID: CP-3.1
TITLE: CP-3(1) Simulated Events
STATEMENT: >>>
Incorporate simulated events into contingency training to facilitate effective response by personnel in crisis situations.
<<<
COMMENT: Baselines: High
BASELINE: High
STATUS: Draft

[REQUIREMENT]
UID: CP-3.2
TITLE: CP-3(2) Mechanisms Used in Training Environments
STATEMENT: >>>
Employ mechanisms used in operations to provide a more thorough and realistic contingency training environment.
<<<
BASELINE: None
STATUS: Draft

[REQUIREMENT]
UID: CP-4
TITLE: CP-4 Contingency Plan Testing
STATEMENT: >>>
a. Test the contingency plan for the system [frequency] using the following tests to determine the effectiveness of the plan and the readiness to execute the plan: [organization-defined tests].

b. Review the contingency plan test results; and

c. Initiate corrective actions, if needed.
<<<
COMMENT: Baselines: Low, Moderate, High
BASELINE: Low
STATUS: Draft

[REQUIREMENT]
UID: CP-4.1
TITLE: CP-4(1) Coordinate with Related Plans
STATEMENT: >>>
Coordinate contingency plan testing with organizational elements responsible for related plans.
<<<
COMMENT: Baselines: Moderate, High
BASELINE: Moderate
STATUS: Draft

[REQUIREMENT]
UID: CP-4.2
TITLE: CP-4(2) Alternate Processing Site
STATEMENT: >>>
Test the contingency plan at the alternate processing site:

  (a) To familiarize contingency personnel with the facility and available resources; and

  (b) To evaluate the capabilities of the alternate processing site to support contingency operations.
<<<
COMMENT: Baselines: High
BASELINE: High
STATUS: Draft

[REQUIREMENT]
UID: CP-4.3
TITLE: CP-4(3) Automated Testing
STATEMENT: >>>
Test the contingency plan using [automated mechanisms].
<<<
BASELINE: None
STATUS: Draft

[REQUIREMENT]
UID: CP-4.4
TITLE: CP-4(4) Full Recovery and Reconstitution
STATEMENT: >>>
Include a full recovery and reconstitution of the system to a known state as part of contingency plan testing.
<<<
BASELINE: None
STATUS: Draft

[REQUIREMENT]
UID: CP-4.5
TITLE: CP-4(5) Self-challenge
STATEMENT: >>>
Employ [mechanisms] to [system or system component] to disrupt and adversely affect the system or system component.
<<<
BASELINE: None
STATUS: Draft

[REQUIREMENT]
UID: CP-5
TITLE: CP-5 Contingency Plan Update
STATEMENT: >>>
Withdrawn. Incorporated into CP-2.
<<<
COMMENT: Withdrawn
BASELINE: None
STATUS: Draft

[REQUIREMENT]
UID: CP-6
TITLE: CP-6 Alternate Storage Site
STATEMENT: >>>
a. Establish an alternate storage site, including necessary agreements to permit the storage and retrieval of system backup information; and

b. Ensure that the alternate storage site provides controls equivalent to that of the primary site.
<<<
COMMENT: Baselines: Moderate, High
BASELINE: Moderate
STATUS: Draft

[REQUIREMENT]
UID: CP-6.1
TITLE: CP-6(1) Separation from Primary Site
STATEMENT: >>>
Identify an alternate storage site that is sufficiently separated from the primary storage site to reduce susceptibility to the same threats.
<<<
COMMENT: Baselines: Moderate, High
BASELINE: Moderate
STATUS: Draft

[REQUIREMENT]
UID: CP-6.2
TITLE: CP-6(2) Recovery Time and Recovery Point Objectives
STATEMENT: >>>
Configure the alternate storage site to facilitate recovery operations in accordance with recovery time and recovery point objectives.
<<<
COMMENT: Baselines: High
BASELINE: High
STATUS: Draft

[REQUIREMENT]
UID: CP-6.3
TITLE: CP-6(3) Accessibility
STATEMENT: >>>
Identify potential accessibility problems to the alternate storage site in the event of an area-wide disruption or disaster and outline explicit mitigation actions.
<<<
COMMENT: Baselines: Moderate, High
BASELINE: Moderate
STATUS: Draft

[REQUIREMENT]
UID: CP-7
TITLE: CP-7 Alternate Processing Site
STATEMENT: >>>
a. Establish an alternate processing site, including necessary agreements to permit the transfer and resumption of [system operations] for essential mission and business functions within [time period] when the primary processing capabilities are unavailable;

b. Make available at the alternate processing site, the equipment and supplies required to transfer and resume operations or put contracts in place to support delivery to the site within the organization-defined time period for transfer and resumption; and

c. Provide controls at the alternate processing site that are equivalent to those at the primary site.
<<<
COMMENT: Baselines: Moderate, High
BASELINE: Moderate
STATUS: Draft

[REQUIREMENT]
UID: CP-7.1
TITLE: CP-7(1) Separation from Primary Site
STATEMENT: >>>
Identify an alternate processing site that is sufficiently separated from the primary processing site to reduce susceptibility to the same threats.
<<<
COMMENT: Baselines: Moderate, High
BASELINE: Moderate
STATUS: Draft

[REQUIREMENT]
UID: CP-7.2
TITLE: CP-7(2) Accessibility
STATEMENT: >>>
Identify potential accessibility problems to alternate processing sites in the event of an area-wide disruption or disaster and outlines explicit mitigation actions.
<<<
COMMENT: Baselines: Moderate, High
BASELINE: Moderate
STATUS: Draft

[REQUIREMENT]
UID: CP-7.3
TITLE: CP-7(3) Priority of Service
STATEMENT: >>>
Develop alternate processing site agreements that contain priority-of-service provisions in accordance with availability requirements (including recovery time objectives).
<<<
COMMENT: Baselines: Moderate, High
BASELINE: Moderate
STATUS: Draft

[REQUIREMENT]
UID: CP-7.4
TITLE: CP-7(4) Preparation for Use
STATEMENT: >>>
Prepare the alternate processing site so that the site can serve as the operational site supporting essential mission and business functions.
<<<
COMMENT: Baselines: High
BASELINE: High
STATUS: Draft

[REQUIREMENT]
UID: CP-7.5
TITLE: CP-7(5) Equivalent Information Security Safeguards
STATEMENT: >>>
Withdrawn. Incorporated into CP-7.
<<<
COMMENT: Withdrawn
BASELINE: None
STATUS: Draft

[REQUIREMENT]
UID: CP-7.6
TITLE: CP-7(6) Inability to Return to Primary Site
STATEMENT: >>>
Plan and prepare for circumstances that preclude returning to the primary processing site.
<<<
BASELINE: None
STATUS: Draft

[REQUIREMENT]
UID: CP-8
TITLE: CP-8 Telecommunications Services
STATEMENT: >>>
Establish alternate telecommunications services, including necessary agreements to permit the resumption of [system operations] for essential mission and business functions within [time period] when the primary telecommunications capabilities are unavailable at either the primary or alternate processing or storage sites.
<<<
COMMENT: Baselines: Moderate, High
BASELINE: Moderate
STATUS: Draft

[REQUIREMENT]
UID: CP-8.1
TITLE: CP-8(1) Priority of Service Provisions
STATEMENT: >>>
(a) Develop primary and alternate telecommunications service agreements that contain priority-of-service provisions in accordance with availability requirements (including recovery time objectives); and

(b) Request Telecommunications Service Priority for all telecommunications services used for national security emergency preparedness if the primary and/or alternate telecommunications services are provided by a common carrier.
<<<
COMMENT: Baselines: Moderate, High
BASELINE: Moderate
STATUS: Draft

[REQUIREMENT]
UID: CP-8.2
TITLE: CP-8(2) Single Points of Failure
STATEMENT: >>>
Obtain alternate telecommunications services to reduce the likelihood of sharing a single point of failure with primary telecommunications services.
<<<
COMMENT: Baselines: Moderate, High
BASELINE: Moderate
STATUS: Draft

[REQUIREMENT]
UID: CP-8.3
TITLE: CP-8(3) Separation of Primary and Alternate Providers
STATEMENT: >>>
Obtain alternate telecommunications services from providers that are separated from primary service providers to reduce susceptibility to the same threats.
<<<
COMMENT: Baselines: High
BASELINE: High
STATUS: Draft

[REQUIREMENT]
UID: CP-8.4
TITLE: CP-8(4) Provider Contingency Plan
STATEMENT: >>>
(a) Require primary and alternate telecommunications service providers to have contingency plans;

(b) Review provider contingency plans to ensure that the plans meet organizational contingency requirements; and

(c) Obtain evidence of contingency testing and training by providers [organization-defined frequency].
<<<
COMMENT: Baselines: High
BASELINE: High
STATUS: Draft

[REQUIREMENT]
UID: CP-8.5
TITLE: CP-8(5) Alternate Telecommunication Service Testing
STATEMENT: >>>
Test alternate telecommunication services [frequency].
<<<
BASELINE: None
STATUS: Draft

[REQUIREMENT]
UID: CP-9
TITLE: CP-9 System Backup
STATEMENT: >>>
a. Conduct backups of user-level information contained in [system components] [frequency];

b. Conduct backups of system-level information contained in the system [frequency];

c. Conduct backups of system documentation, including security- and privacy-related documentation [frequency] ; and

d. Protect the confidentiality, integrity, and availability of backup information.
<<<
COMMENT: Baselines: Low, Moderate, High
BASELINE: Low
STATUS: Draft

[REQUIREMENT]
UID: CP-9.1
TITLE: CP-9(1) Testing for Reliability and Integrity
STATEMENT: >>>
Test backup information [organization-defined frequency] to verify media reliability and information integrity.
<<<
COMMENT: Baselines: Moderate, High
BASELINE: Moderate
STATUS: Draft

[REQUIREMENT]
UID: CP-9.2
TITLE: CP-9(2) Test Restoration Using Sampling
STATEMENT: >>>
Use a sample of backup information in the restoration of selected system functions as part of contingency plan testing.
<<<
COMMENT: Baselines: High
BASELINE: High
STATUS: Draft

[REQUIREMENT]
UID: CP-9.3
TITLE: CP-9(3) Separate Storage for Critical Information
STATEMENT: >>>
Store backup copies of [critical system software and other security-related information] in a separate facility or in a fire rated container that is not collocated with the operational system.
<<<
COMMENT: Baselines: High
BASELINE: High
STATUS: Draft

[REQUIREMENT]
UID: CP-9.4
TITLE: CP-9(4) Protection from Unauthorized Modification
STATEMENT: >>>
Withdrawn. Incorporated into CP-9.
<<<
COMMENT: Withdrawn
BASELINE: None
STATUS: Draft

[REQUIREMENT]
UID: CP-9.5
TITLE: CP-9(5) Transfer to Alternate Storage Site
STATEMENT: >>>
Transfer system backup information to the alternate storage site [organization-defined time period and transfer rate consistent with the recovery time and recovery point objectives].
<<<
COMMENT: Baselines: High
BASELINE: High
STATUS: Draft

[REQUIREMENT]
UID: CP-9.6
TITLE: CP-9(6) Redundant Secondary System
STATEMENT: >>>
Conduct system backup by maintaining a redundant secondary system that is not collocated with the primary system and that can be activated without loss of information or disruption to operations.
<<<
BASELINE: None
STATUS: Draft

[REQUIREMENT]
UID: CP-9.7
TITLE: CP-9(7) Dual Authorization for Deletion or Destruction
STATEMENT: >>>
Enforce dual authorization for the deletion or destruction of [backup information].
<<<
BASELINE: None
STATUS: Draft

[REQUIREMENT]
UID: CP-9.8
TITLE: CP-9(8) Cryptographic Protection
STATEMENT: >>>
Implement cryptographic mechanisms to prevent unauthorized disclosure and modification of [backup information].
<<<
COMMENT: Baselines: Moderate, High
BASELINE: Moderate
STATUS: Draft

[REQUIREMENT]
UID: CP-10
TITLE: CP-10 System Recovery and Reconstitution
STATEMENT: >>>
Provide for the recovery and reconstitution of the system to a known state within [organization-defined time period consistent with recovery time and recovery point objectives] after a disruption, compromise, or failure.
<<<
COMMENT: Baselines: Low, Moderate, High
BASELINE: Low
STATUS: Draft

[REQUIREMENT]
UID: CP-10.1
TITLE: CP-10(1) Contingency Plan Testing
STATEMENT: >>>
Withdrawn. Incorporated into CP-4.
<<<
COMMENT: Withdrawn
BASELINE: None
STATUS: Draft

[REQUIREMENT]
UID: CP-10.2
TITLE: CP-10(2) Transaction Recovery
STATEMENT: >>>
Implement transaction recovery for systems that are transaction-based.
<<<
COMMENT: Baselines: Moderate, High
BASELINE: Moderate
STATUS: Draft

[REQUIREMENT]
UID: CP-10.3
TITLE: CP-10(3) Compensating Security Controls
STATEMENT: >>>
Withdrawn.
Addressed through tailoring.
<<<
COMMENT: Withdrawn
BASELINE: None
STATUS: Draft

[REQUIREMENT]
UID: CP-10.4
TITLE: CP-10(4) Restore Within Time Period
STATEMENT: >>>
Provide the capability to restore system components within [restoration time periods] from configuration-controlled and integrity-protected information representing a known, operational state for the components.
<<<
COMMENT: Baselines: High
BASELINE: High
STATUS: Draft

[REQUIREMENT]
UID: CP-10.5
TITLE: CP-10(5) Failover Capability
STATEMENT: >>>
Withdrawn. Incorporated into SI-13.
<<<
COMMENT: Withdrawn
BASELINE: None
STATUS: Draft

[REQUIREMENT]
UID: CP-10.6
TITLE: CP-10(6) Component Protection
STATEMENT: >>>
Protect system components used for recovery and reconstitution.
<<<
BASELINE: None
STATUS: Draft

[REQUIREMENT]
UID: CP-11
TITLE: CP-11 Alternate Communications Protocols
STATEMENT: >>>
Provide the capability to employ [alternative communications protocols] in support of maintaining continuity of operations.
<<<
BASELINE: None
STATUS: Draft

[REQUIREMENT]
UID: CP-12
TITLE: CP-12 Safe Mode
STATEMENT: >>>
When [conditions] are detected, enter a safe mode of operation with [restrictions].
<<<
BASELINE: None
STATUS: Draft

[REQUIREMENT]
UID: CP-13
TITLE: CP-13 Alternative Security Mechanisms
STATEMENT: >>>
Employ [alternative or supplemental security mechanisms] for satisfying [security functions] when the primary means of implementing the security function is unavailable or compromised.
<<<
BASELINE: None
STATUS: Draft

[[/SECTION]]

[[SECTION]]
UID: NIST-IA
TITLE: IA — Identification and Authentication

[REQUIREMENT]
UID: IA-1
TITLE: IA-1 Policy and Procedures
STATEMENT: >>>
a. Develop, document, and disseminate to [organization-defined personnel or roles]:

  1. [ia-01_odp.03] identification and authentication policy that:

    (a) Addresses purpose, scope, roles, responsibilities, management commitment, coordination among organizational entities, and compliance; and

    (b) Is consistent with applicable laws, executive orders, directives, regulations, policies, standards, and guidelines; and

  2. Procedures to facilitate the implementation of the identification and authentication policy and the associated identification and authentication controls;

b. Designate an [official] to manage the development, documentation, and dissemination of the identification and authentication policy and procedures; and

c. Review and update the current identification and authentication:

  1. Policy [frequency] and following [events] ; and

  2. Procedures [frequency] and following [events].
<<<
COMMENT: Baselines: Low, Moderate, High
BASELINE: Low
STATUS: Draft

[REQUIREMENT]
UID: IA-2
TITLE: IA-2 Identification and Authentication (Organizational Users)
STATEMENT: >>>
Uniquely identify and authenticate organizational users and associate that unique identification with processes acting on behalf of those users.
<<<
COMMENT: Baselines: Low, Moderate, High
BASELINE: Low
STATUS: Draft

[REQUIREMENT]
UID: IA-2.1
TITLE: IA-2(1) Multi-factor Authentication to Privileged Accounts
STATEMENT: >>>
Implement multi-factor authentication for access to privileged accounts.
<<<
COMMENT: Baselines: Low, Moderate, High
BASELINE: Low
STATUS: Draft

[REQUIREMENT]
UID: IA-2.2
TITLE: IA-2(2) Multi-factor Authentication to Non-privileged Accounts
STATEMENT: >>>
Implement multi-factor authentication for access to non-privileged accounts.
<<<
COMMENT: Baselines: Low, Moderate, High
BASELINE: Low
STATUS: Draft

[REQUIREMENT]
UID: IA-2.3
TITLE: IA-2(3) Local Access to Privileged Accounts
STATEMENT: >>>
Withdrawn. Incorporated into IA-2.1.
<<<
COMMENT: Withdrawn
BASELINE: None
STATUS: Draft

[REQUIREMENT]
UID: IA-2.4
TITLE: IA-2(4) Local Access to Non-privileged Accounts
STATEMENT: >>>
Withdrawn. Incorporated into IA-2.2.
<<<
COMMENT: Withdrawn
BASELINE: None
STATUS: Draft

[REQUIREMENT]
UID: IA-2.5
TITLE: IA-2(5) Individual Authentication with Group Authentication
STATEMENT: >>>
When shared accounts or authenticators are employed, require users to be individually authenticated before granting access to the shared accounts or resources.
<<<
COMMENT: Baselines: High
BASELINE: High
STATUS: Draft

[REQUIREMENT]
UID: IA-2.6
TITLE: IA-2(6) Access to Accounts —separate Device
STATEMENT: >>>
Implement multi-factor authentication for [ia-02.06_odp.01] access to [ia-02.06_odp.02] such that:

  (a) One of the factors is provided by a device separate from the system gaining access; and

  (b) The device meets [strength of mechanism requirements].
<<<
BASELINE: None
STATUS: Draft

[REQUIREMENT]
UID: IA-2.7
TITLE: IA-2(7) Network Access to Non-privileged Accounts — Separate Device
STATEMENT: >>>
Withdrawn. Incorporated into IA-2.6.
<<<
COMMENT: Withdrawn
BASELINE: None
STATUS: Draft

[REQUIREMENT]
UID: IA-2.8
TITLE: IA-2(8) Access to Accounts — Replay Resistant
STATEMENT: >>>
Implement replay-resistant authentication mechanisms for access to [ia-02.08_odp].
<<<
COMMENT: Baselines: Low, Moderate, High
BASELINE: Low
STATUS: Draft

[REQUIREMENT]
UID: IA-2.9
TITLE: IA-2(9) Network Access to Non-privileged Accounts — Replay Resistant
STATEMENT: >>>
Withdrawn. Incorporated into IA-2.8.
<<<
COMMENT: Withdrawn
BASELINE: None
STATUS: Draft

[REQUIREMENT]
UID: IA-2.10
TITLE: IA-2(10) Single Sign-on
STATEMENT: >>>
Provide a single sign-on capability for [system accounts and services].
<<<
BASELINE: None
STATUS: Draft

[REQUIREMENT]
UID: IA-2.11
TITLE: IA-2(11) Remote Access — Separate Device
STATEMENT: >>>
Withdrawn. Incorporated into IA-2.6.
<<<
COMMENT: Withdrawn
BASELINE: None
STATUS: Draft

[REQUIREMENT]
UID: IA-2.12
TITLE: IA-2(12) Acceptance of PIV Credentials
STATEMENT: >>>
Accept and electronically verify Personal Identity Verification-compliant credentials.
<<<
COMMENT: Baselines: Low, Moderate, High
BASELINE: Low
STATUS: Draft

[REQUIREMENT]
UID: IA-2.13
TITLE: IA-2(13) Out-of-band Authentication
STATEMENT: >>>
Implement the following out-of-band authentication mechanisms under [conditions]: [out-of-band authentication].
<<<
BASELINE: None
STATUS: Draft

[REQUIREMENT]
UID: IA-3
TITLE: IA-3 Device Identification and Authentication
STATEMENT: >>>
Uniquely identify and authenticate [devices and/or types of devices] before establishing a [ia-03_odp.02] connection.
<<<
COMMENT: Baselines: Moderate, High
BASELINE: Moderate
STATUS: Draft

[REQUIREMENT]
UID: IA-3.1
TITLE: IA-3(1) Cryptographic Bidirectional Authentication
STATEMENT: >>>
Authenticate [devices and/or types of devices] before establishing [ia-03.01_odp.02] connection using bidirectional authentication that is cryptographically based.
<<<
BASELINE: None
STATUS: Draft

[REQUIREMENT]
UID: IA-3.2
TITLE: IA-3(2) Cryptographic Bidirectional Network Authentication
STATEMENT: >>>
Withdrawn. Incorporated into IA-3.1.
<<<
COMMENT: Withdrawn
BASELINE: None
STATUS: Draft

[REQUIREMENT]
UID: IA-3.3
TITLE: IA-3(3) Dynamic Address Allocation
STATEMENT: >>>
(a) Where addresses are allocated dynamically, standardize dynamic address allocation lease information and the lease duration assigned to devices in accordance with [organization-defined lease information and lease duration] ; and

(b) Audit lease information when assigned to a device.
<<<
BASELINE: None
STATUS: Draft

[REQUIREMENT]
UID: IA-3.4
TITLE: IA-3(4) Device Attestation
STATEMENT: >>>
Handle device identification and authentication based on attestation by [configuration management process].
<<<
BASELINE: None
STATUS: Draft

[REQUIREMENT]
UID: IA-4
TITLE: IA-4 Identifier Management
STATEMENT: >>>
Manage system identifiers by:

  a. Receiving authorization from [personnel or roles] to assign an individual, group, role, service, or device identifier;

  b. Selecting an identifier that identifies an individual, group, role, service, or device;

  c. Assigning the identifier to the intended individual, group, role, service, or device; and

  d. Preventing reuse of identifiers for [time period].
<<<
COMMENT: Baselines: Low, Moderate, High
BASELINE: Low
STATUS: Draft

[REQUIREMENT]
UID: IA-4.1
TITLE: IA-4(1) Prohibit Account Identifiers as Public Identifiers
STATEMENT: >>>
Prohibit the use of system account identifiers that are the same as public identifiers for individual accounts.
<<<
BASELINE: None
STATUS: Draft

[REQUIREMENT]
UID: IA-4.2
TITLE: IA-4(2) Supervisor Authorization
STATEMENT: >>>
Withdrawn. Incorporated into IA-12.1.
<<<
COMMENT: Withdrawn
BASELINE: None
STATUS: Draft

[REQUIREMENT]
UID: IA-4.3
TITLE: IA-4(3) Multiple Forms of Certification
STATEMENT: >>>
Withdrawn. Incorporated into IA-12.2.
<<<
COMMENT: Withdrawn
BASELINE: None
STATUS: Draft

[REQUIREMENT]
UID: IA-4.4
TITLE: IA-4(4) Identify User Status
STATEMENT: >>>
Manage individual identifiers by uniquely identifying each individual as [characteristics].
<<<
COMMENT: Baselines: Moderate, High
BASELINE: Moderate
STATUS: Draft

[REQUIREMENT]
UID: IA-4.5
TITLE: IA-4(5) Dynamic Management
STATEMENT: >>>
Manage individual identifiers dynamically in accordance with [dynamic identifier policy].
<<<
BASELINE: None
STATUS: Draft

[REQUIREMENT]
UID: IA-4.6
TITLE: IA-4(6) Cross-organization Management
STATEMENT: >>>
Coordinate with the following external organizations for cross-organization management of identifiers: [external organizations].
<<<
BASELINE: None
STATUS: Draft

[REQUIREMENT]
UID: IA-4.7
TITLE: IA-4(7) In-person Registration
STATEMENT: >>>
Withdrawn. Incorporated into IA-12.4.
<<<
COMMENT: Withdrawn
BASELINE: None
STATUS: Draft

[REQUIREMENT]
UID: IA-4.8
TITLE: IA-4(8) Pairwise Pseudonymous Identifiers
STATEMENT: >>>
Generate pairwise pseudonymous identifiers.
<<<
BASELINE: None
STATUS: Draft

[REQUIREMENT]
UID: IA-4.9
TITLE: IA-4(9) Attribute Maintenance and Protection
STATEMENT: >>>
Maintain the attributes for each uniquely identified individual, device, or service in [protected central storage].
<<<
BASELINE: None
STATUS: Draft

[REQUIREMENT]
UID: IA-5
TITLE: IA-5 Authenticator Management
STATEMENT: >>>
Manage system authenticators by:

  a. Verifying, as part of the initial authenticator distribution, the identity of the individual, group, role, service, or device receiving the authenticator;

  b. Establishing initial authenticator content for any authenticators issued by the organization;

  c. Ensuring that authenticators have sufficient strength of mechanism for their intended use;

  d. Establishing and implementing administrative procedures for initial authenticator distribution, for lost or compromised or damaged authenticators, and for revoking authenticators;

  e. Changing default authenticators prior to first use;

  f. Changing or refreshing authenticators [time period by authenticator type] or when [events] occur;

  g. Protecting authenticator content from unauthorized disclosure and modification;

  h. Requiring individuals to take, and having devices implement, specific controls to protect authenticators; and

  i. Changing authenticators for group or role accounts when membership to those accounts changes.
<<<
COMMENT: Baselines: Low, Moderate, High
BASELINE: Low
STATUS: Draft

[REQUIREMENT]
UID: IA-5.1
TITLE: IA-5(1) Password-based Authentication
STATEMENT: >>>
For password-based authentication:

  (a) Maintain a list of commonly-used, expected, or compromised passwords and update the list [frequency] and when organizational passwords are suspected to have been compromised directly or indirectly;

  (b) Verify, when users create or update passwords, that the passwords are not found on the list of commonly-used, expected, or compromised passwords in IA-5(1)(a);

  (c) Transmit passwords only over cryptographically-protected channels;

  (d) Store passwords using an approved salted key derivation function, preferably using a keyed hash;

  (e) Require immediate selection of a new password upon account recovery;

  (f) Allow user selection of long passwords and passphrases, including spaces and all printable characters;

  (g) Employ automated tools to assist the user in selecting strong password authenticators; and

  (h) Enforce the following composition and complexity rules: [composition and complexity rules].
<<<
COMMENT: Baselines: Low, Moderate, High
BASELINE: Low
STATUS: Draft

[REQUIREMENT]
UID: IA-5.2
TITLE: IA-5(2) Public Key-based Authentication
STATEMENT: >>>
(a) For public key-based authentication:

  (1) Enforce authorized access to the corresponding private key; and

  (2) Map the authenticated identity to the account of the individual or group; and

(b) When public key infrastructure (PKI) is used:

  (1) Validate certificates by constructing and verifying a certification path to an accepted trust anchor, including checking certificate status information; and

  (2) Implement a local cache of revocation data to support path discovery and validation.
<<<
COMMENT: Baselines: Moderate, High
BASELINE: Moderate
STATUS: Draft

[REQUIREMENT]
UID: IA-5.3
TITLE: IA-5(3) In-person or Trusted External Party Registration
STATEMENT: >>>
Withdrawn. Incorporated into IA-12.4.
<<<
COMMENT: Withdrawn
BASELINE: None
STATUS: Draft

[REQUIREMENT]
UID: IA-5.4
TITLE: IA-5(4) Automated Support for Password Strength Determination
STATEMENT: >>>
Withdrawn. Incorporated into IA-5.1.
<<<
COMMENT: Withdrawn
BASELINE: None
STATUS: Draft

[REQUIREMENT]
UID: IA-5.5
TITLE: IA-5(5) Change Authenticators Prior to Delivery
STATEMENT: >>>
Require developers and installers of system components to provide unique authenticators or change default authenticators prior to delivery and installation.
<<<
BASELINE: None
STATUS: Draft

[REQUIREMENT]
UID: IA-5.6
TITLE: IA-5(6) Protection of Authenticators
STATEMENT: >>>
Protect authenticators commensurate with the security category of the information to which use of the authenticator permits access.
<<<
COMMENT: Baselines: Moderate, High
BASELINE: Moderate
STATUS: Draft

[REQUIREMENT]
UID: IA-5.7
TITLE: IA-5(7) No Embedded Unencrypted Static Authenticators
STATEMENT: >>>
Ensure that unencrypted static authenticators are not embedded in applications or other forms of static storage.
<<<
BASELINE: None
STATUS: Draft

[REQUIREMENT]
UID: IA-5.8
TITLE: IA-5(8) Multiple System Accounts
STATEMENT: >>>
Implement [security controls] to manage the risk of compromise due to individuals having accounts on multiple systems.
<<<
BASELINE: None
STATUS: Draft

[REQUIREMENT]
UID: IA-5.9
TITLE: IA-5(9) Federated Credential Management
STATEMENT: >>>
Use the following external organizations to federate credentials: [external organizations].
<<<
BASELINE: None
STATUS: Draft

[REQUIREMENT]
UID: IA-5.10
TITLE: IA-5(10) Dynamic Credential Binding
STATEMENT: >>>
Bind identities and authenticators dynamically using the following rules: [binding rules].
<<<
BASELINE: None
STATUS: Draft

[REQUIREMENT]
UID: IA-5.11
TITLE: IA-5(11) Hardware Token-based Authentication
STATEMENT: >>>
Withdrawn. Incorporated into IA-2.1, IA-2.2.
<<<
COMMENT: Withdrawn
BASELINE: None
STATUS: Draft

[REQUIREMENT]
UID: IA-5.12
TITLE: IA-5(12) Biometric Authentication Performance
STATEMENT: >>>
For biometric-based authentication, employ mechanisms that satisfy the following biometric quality requirements [biometric quality requirements].
<<<
BASELINE: None
STATUS: Draft

[REQUIREMENT]
UID: IA-5.13
TITLE: IA-5(13) Expiration of Cached Authenticators
STATEMENT: >>>
Prohibit the use of cached authenticators after [time period].
<<<
BASELINE: None
STATUS: Draft

[REQUIREMENT]
UID: IA-5.14
TITLE: IA-5(14) Managing Content of PKI Trust Stores
STATEMENT: >>>
For PKI-based authentication, employ an organization-wide methodology for managing the content of PKI trust stores installed across all platforms, including networks, operating systems, browsers, and applications.
<<<
BASELINE: None
STATUS: Draft

[REQUIREMENT]
UID: IA-5.15
TITLE: IA-5(15) GSA-approved Products and Services
STATEMENT: >>>
Use only General Services Administration-approved products and services for identity, credential, and access management.
<<<
BASELINE: None
STATUS: Draft

[REQUIREMENT]
UID: IA-5.16
TITLE: IA-5(16) In-person or Trusted External Party Authenticator Issuance
STATEMENT: >>>
Require that the issuance of [types of and/or specific authenticators] be conducted [ia-05.16_odp.02] before [registration authority] with authorization by [personnel or roles].
<<<
BASELINE: None
STATUS: Draft

[REQUIREMENT]
UID: IA-5.17
TITLE: IA-5(17) Presentation Attack Detection for Biometric Authenticators
STATEMENT: >>>
Employ presentation attack detection mechanisms for biometric-based authentication.
<<<
BASELINE: None
STATUS: Draft

[REQUIREMENT]
UID: IA-5.18
TITLE: IA-5(18) Password Managers
STATEMENT: >>>
(a) Employ [password managers] to generate and manage passwords; and

(b) Protect the passwords using [controls].
<<<
BASELINE: None
STATUS: Draft

[REQUIREMENT]
UID: IA-6
TITLE: IA-6 Authentication Feedback
STATEMENT: >>>
Obscure feedback of authentication information during the authentication process to protect the information from possible exploitation and use by unauthorized individuals.
<<<
COMMENT: Baselines: Low, Moderate, High
BASELINE: Low
STATUS: Draft

[REQUIREMENT]
UID: IA-7
TITLE: IA-7 Cryptographic Module Authentication
STATEMENT: >>>
Implement mechanisms for authentication to a cryptographic module that meet the requirements of applicable laws, executive orders, directives, policies, regulations, standards, and guidelines for such authentication.
<<<
COMMENT: Baselines: Low, Moderate, High
BASELINE: Low
STATUS: Draft

[REQUIREMENT]
UID: IA-8
TITLE: IA-8 Identification and Authentication (Non-organizational Users)
STATEMENT: >>>
Uniquely identify and authenticate non-organizational users or processes acting on behalf of non-organizational users.
<<<
COMMENT: Baselines: Low, Moderate, High
BASELINE: Low
STATUS: Draft

[REQUIREMENT]
UID: IA-8.1
TITLE: IA-8(1) Acceptance of PIV Credentials from Other Agencies
STATEMENT: >>>
Accept and electronically verify Personal Identity Verification-compliant credentials from other federal agencies.
<<<
COMMENT: Baselines: Low, Moderate, High
BASELINE: Low
STATUS: Draft

[REQUIREMENT]
UID: IA-8.2
TITLE: IA-8(2) Acceptance of External Authenticators
STATEMENT: >>>
(a) Accept only external authenticators that are NIST-compliant; and

(b) Document and maintain a list of accepted external authenticators.
<<<
COMMENT: Baselines: Low, Moderate, High
BASELINE: Low
STATUS: Draft

[REQUIREMENT]
UID: IA-8.3
TITLE: IA-8(3) Use of FICAM-approved Products
STATEMENT: >>>
Withdrawn. Incorporated into IA-8.2.
<<<
COMMENT: Withdrawn
BASELINE: None
STATUS: Draft

[REQUIREMENT]
UID: IA-8.4
TITLE: IA-8(4) Use of Defined Profiles
STATEMENT: >>>
Conform to the following profiles for identity management [identity management profiles].
<<<
COMMENT: Baselines: Low, Moderate, High
BASELINE: Low
STATUS: Draft

[REQUIREMENT]
UID: IA-8.5
TITLE: IA-8(5) Acceptance of PIV-I Credentials
STATEMENT: >>>
Accept and verify federated or PKI credentials that meet [policy].
<<<
BASELINE: None
STATUS: Draft

[REQUIREMENT]
UID: IA-8.6
TITLE: IA-8(6) Disassociability
STATEMENT: >>>
Implement the following measures to disassociate user attributes or identifier assertion relationships among individuals, credential service providers, and relying parties: [measures].
<<<
BASELINE: None
STATUS: Draft

[REQUIREMENT]
UID: IA-9
TITLE: IA-9 Service Identification and Authentication
STATEMENT: >>>
Uniquely identify and authenticate [system services and applications] before establishing communications with devices, users, or other services or applications.
<<<
BASELINE: None
STATUS: Draft

[REQUIREMENT]
UID: IA-9.1
TITLE: IA-9(1) Information Exchange
STATEMENT: >>>
Withdrawn. Incorporated into IA-9.
<<<
COMMENT: Withdrawn
BASELINE: None
STATUS: Draft

[REQUIREMENT]
UID: IA-9.2
TITLE: IA-9(2) Transmission of Decisions
STATEMENT: >>>
Withdrawn. Incorporated into IA-9.
<<<
COMMENT: Withdrawn
BASELINE: None
STATUS: Draft

[REQUIREMENT]
UID: IA-10
TITLE: IA-10 Adaptive Authentication
STATEMENT: >>>
Require individuals accessing the system to employ [supplemental authentication techniques or mechanisms] under specific [circumstances or situations].
<<<
BASELINE: None
STATUS: Draft

[REQUIREMENT]
UID: IA-11
TITLE: IA-11 Re-authentication
STATEMENT: >>>
Require users to re-authenticate when [circumstances or situations].
<<<
COMMENT: Baselines: Low, Moderate, High
BASELINE: Low
STATUS: Draft

[REQUIREMENT]
UID: IA-12
TITLE: IA-12 Identity Proofing
STATEMENT: >>>
a. Identity proof users that require accounts for logical access to systems based on appropriate identity assurance level requirements as specified in applicable standards and guidelines;

b. Resolve user identities to a unique individual; and

c. Collect, validate, and verify identity evidence.
<<<
COMMENT: Baselines: Moderate, High
BASELINE: Moderate
STATUS: Draft

[REQUIREMENT]
UID: IA-12.1
TITLE: IA-12(1) Supervisor Authorization
STATEMENT: >>>
Require that the registration process to receive an account for logical access includes supervisor or sponsor authorization.
<<<
BASELINE: None
STATUS: Draft

[REQUIREMENT]
UID: IA-12.2
TITLE: IA-12(2) Identity Evidence
STATEMENT: >>>
Require evidence of individual identification be presented to the registration authority.
<<<
COMMENT: Baselines: Moderate, High
BASELINE: Moderate
STATUS: Draft

[REQUIREMENT]
UID: IA-12.3
TITLE: IA-12(3) Identity Evidence Validation and Verification
STATEMENT: >>>
Require that the presented identity evidence be validated and verified through [methods of validation and verification].
<<<
COMMENT: Baselines: Moderate, High
BASELINE: Moderate
STATUS: Draft

[REQUIREMENT]
UID: IA-12.4
TITLE: IA-12(4) In-person Validation and Verification
STATEMENT: >>>
Require that the validation and verification of identity evidence be conducted in person before a designated registration authority.
<<<
COMMENT: Baselines: High
BASELINE: High
STATUS: Draft

[REQUIREMENT]
UID: IA-12.5
TITLE: IA-12(5) Address Confirmation
STATEMENT: >>>
Require that a [ia-12.05_odp] be delivered through an out-of-band channel to verify the users address (physical or digital) of record.
<<<
COMMENT: Baselines: Moderate, High
BASELINE: Moderate
STATUS: Draft

[REQUIREMENT]
UID: IA-12.6
TITLE: IA-12(6) Accept Externally-proofed Identities
STATEMENT: >>>
Accept externally-proofed identities at [identity assurance level].
<<<
BASELINE: None
STATUS: Draft

[REQUIREMENT]
UID: IA-13
TITLE: IA-13 Identity Providers and Authorization Servers
STATEMENT: >>>
Employ identity providers and authorization servers to manage user, device, and non-person entity (NPE) identities, attributes, and access rights supporting authentication and authorization decisions in accordance with [policy] using [mechanisms].
<<<
BASELINE: None
STATUS: Draft

[REQUIREMENT]
UID: IA-13.1
TITLE: IA-13(1) Protection of Cryptographic Keys
STATEMENT: >>>
Cryptographic keys that protect access tokens are generated, managed, and protected from disclosure and misuse.
<<<
BASELINE: None
STATUS: Draft

[REQUIREMENT]
UID: IA-13.2
TITLE: IA-13(2) Verification of Identity Assertions and Access Tokens
STATEMENT: >>>
The source and integrity of identity assertions and access tokens are verified before granting access to system and information resources.
<<<
BASELINE: None
STATUS: Draft

[REQUIREMENT]
UID: IA-13.3
TITLE: IA-13(3) Token Management
STATEMENT: >>>
In accordance with [ia-13_odp.01], assertions and access tokens are:

  (a) generated;

  (b) issued;

  (c) refreshed;

  (d) revoked;

  (e) time-restricted; and

  (f) audience-restricted.
<<<
BASELINE: None
STATUS: Draft

[[/SECTION]]

[[SECTION]]
UID: NIST-IR
TITLE: IR — Incident Response

[REQUIREMENT]
UID: IR-1
TITLE: IR-1 Policy and Procedures
STATEMENT: >>>
a. Develop, document, and disseminate to [organization-defined personnel or roles]:

  1. [ir-01_odp.03] incident response policy that:

    (a) Addresses purpose, scope, roles, responsibilities, management commitment, coordination among organizational entities, and compliance; and

    (b) Is consistent with applicable laws, executive orders, directives, regulations, policies, standards, and guidelines; and

  2. Procedures to facilitate the implementation of the incident response policy and the associated incident response controls;

b. Designate an [official] to manage the development, documentation, and dissemination of the incident response policy and procedures; and

c. Review and update the current incident response:

  1. Policy [frequency] and following [events] ; and

  2. Procedures [frequency] and following [events].
<<<
COMMENT: Baselines: Low, Moderate, High, Privacy
BASELINE: Low
STATUS: Draft

[REQUIREMENT]
UID: IR-2
TITLE: IR-2 Incident Response Training
STATEMENT: >>>
a. Provide incident response training to system users consistent with assigned roles and responsibilities:

  1. Within [time period] of assuming an incident response role or responsibility or acquiring system access;

  2. When required by system changes; and

  3. [frequency] thereafter; and

b. Review and update incident response training content [frequency] and following [events].
<<<
COMMENT: Baselines: Low, Moderate, High, Privacy
BASELINE: Low
STATUS: Draft

[REQUIREMENT]
UID: IR-2.1
TITLE: IR-2(1) Simulated Events
STATEMENT: >>>
Incorporate simulated events into incident response training to facilitate the required response by personnel in crisis situations.
<<<
COMMENT: Baselines: High
BASELINE: High
STATUS: Draft

[REQUIREMENT]
UID: IR-2.2
TITLE: IR-2(2) Automated Training Environments
STATEMENT: >>>
Provide an incident response training environment using [automated mechanisms].
<<<
COMMENT: Baselines: High
BASELINE: High
STATUS: Draft

[REQUIREMENT]
UID: IR-2.3
TITLE: IR-2(3) Breach
STATEMENT: >>>
Provide incident response training on how to identify and respond to a breach, including the organization’s process for reporting a breach.
<<<
COMMENT: Baselines: Privacy
BASELINE: Privacy
STATUS: Draft

[REQUIREMENT]
UID: IR-3
TITLE: IR-3 Incident Response Testing
STATEMENT: >>>
Test the effectiveness of the incident response capability for the system [frequency] using the following tests: [tests].
<<<
COMMENT: Baselines: Moderate, High, Privacy
BASELINE: Moderate
STATUS: Draft

[REQUIREMENT]
UID: IR-3.1
TITLE: IR-3(1) Automated Testing
STATEMENT: >>>
Test the incident response capability using [automated mechanisms].
<<<
BASELINE: None
STATUS: Draft

[REQUIREMENT]
UID: IR-3.2
TITLE: IR-3(2) Coordination with Related Plans
STATEMENT: >>>
Coordinate incident response testing with organizational elements responsible for related plans.
<<<
COMMENT: Baselines: Moderate, High
BASELINE: Moderate
STATUS: Draft

[REQUIREMENT]
UID: IR-3.3
TITLE: IR-3(3) Continuous Improvement
STATEMENT: >>>
Use qualitative and quantitative data from testing to:

  (a) Determine the effectiveness of incident response processes;

  (b) Continuously improve incident response processes; and

  (c) Provide incident response measures and metrics that are accurate, consistent, and in a reproducible format.
<<<
BASELINE: None
STATUS: Draft

[REQUIREMENT]
UID: IR-4
TITLE: IR-4 Incident Handling
STATEMENT: >>>
a. Implement an incident handling capability for incidents that is consistent with the incident response plan and includes preparation, detection and analysis, containment, eradication, and recovery;

b. Coordinate incident handling activities with contingency planning activities;

c. Incorporate lessons learned from ongoing incident handling activities into incident response procedures, training, and testing, and implement the resulting changes accordingly; and

d. Ensure the rigor, intensity, scope, and results of incident handling activities are comparable and predictable across the organization.
<<<
COMMENT: Baselines: Low, Moderate, High, Privacy
BASELINE: Low
STATUS: Draft

[REQUIREMENT]
UID: IR-4.1
TITLE: IR-4(1) Automated Incident Handling Processes
STATEMENT: >>>
Support the incident handling process using [automated mechanisms].
<<<
COMMENT: Baselines: Moderate, High
BASELINE: Moderate
STATUS: Draft

[REQUIREMENT]
UID: IR-4.2
TITLE: IR-4(2) Dynamic Reconfiguration
STATEMENT: >>>
Include the following types of dynamic reconfiguration for [system components] as part of the incident response capability: [types of dynamic reconfiguration].
<<<
BASELINE: None
STATUS: Draft

[REQUIREMENT]
UID: IR-4.3
TITLE: IR-4(3) Continuity of Operations
STATEMENT: >>>
Identify [classes of incidents] and take the following actions in response to those incidents to ensure continuation of organizational mission and business functions: [actions].
<<<
BASELINE: None
STATUS: Draft

[REQUIREMENT]
UID: IR-4.4
TITLE: IR-4(4) Information Correlation
STATEMENT: >>>
Correlate incident information and individual incident responses to achieve an organization-wide perspective on incident awareness and response.
<<<
COMMENT: Baselines: High
BASELINE: High
STATUS: Draft

[REQUIREMENT]
UID: IR-4.5
TITLE: IR-4(5) Automatic Disabling of System
STATEMENT: >>>
Implement a configurable capability to automatically disable the system if [security violations] are detected.
<<<
BASELINE: None
STATUS: Draft

[REQUIREMENT]
UID: IR-4.6
TITLE: IR-4(6) Insider Threats
STATEMENT: >>>
Implement an incident handling capability for incidents involving insider threats.
<<<
BASELINE: None
STATUS: Draft

[REQUIREMENT]
UID: IR-4.7
TITLE: IR-4(7) Insider Threats — Intra-organization Coordination
STATEMENT: >>>
Coordinate an incident handling capability for insider threats that includes the following organizational entities [entities].
<<<
BASELINE: None
STATUS: Draft

[REQUIREMENT]
UID: IR-4.8
TITLE: IR-4(8) Correlation with External Organizations
STATEMENT: >>>
Coordinate with [external organizations] to correlate and share [incident information] to achieve a cross-organization perspective on incident awareness and more effective incident responses.
<<<
BASELINE: None
STATUS: Draft

[REQUIREMENT]
UID: IR-4.9
TITLE: IR-4(9) Dynamic Response Capability
STATEMENT: >>>
Employ [dynamic response capabilities] to respond to incidents.
<<<
BASELINE: None
STATUS: Draft

[REQUIREMENT]
UID: IR-4.10
TITLE: IR-4(10) Supply Chain Coordination
STATEMENT: >>>
Coordinate incident handling activities involving supply chain events with other organizations involved in the supply chain.
<<<
BASELINE: None
STATUS: Draft

[REQUIREMENT]
UID: IR-4.11
TITLE: IR-4(11) Integrated Incident Response Team
STATEMENT: >>>
Establish and maintain an integrated incident response team that can be deployed to any location identified by the organization in [time period].
<<<
COMMENT: Baselines: High
BASELINE: High
STATUS: Draft

[REQUIREMENT]
UID: IR-4.12
TITLE: IR-4(12) Malicious Code and Forensic Analysis
STATEMENT: >>>
Analyze malicious code and/or other residual artifacts remaining in the system after the incident.
<<<
BASELINE: None
STATUS: Draft

[REQUIREMENT]
UID: IR-4.13
TITLE: IR-4(13) Behavior Analysis
STATEMENT: >>>
Analyze anomalous or suspected adversarial behavior in or related to [environments or resources].
<<<
BASELINE: None
STATUS: Draft

[REQUIREMENT]
UID: IR-4.14
TITLE: IR-4(14) Security Operations Center
STATEMENT: >>>
Establish and maintain a security operations center.
<<<
BASELINE: None
STATUS: Draft

[REQUIREMENT]
UID: IR-4.15
TITLE: IR-4(15) Public Relations and Reputation Repair
STATEMENT: >>>
(a) Manage public relations associated with an incident; and

(b) Employ measures to repair the reputation of the organization.
<<<
BASELINE: None
STATUS: Draft

[REQUIREMENT]
UID: IR-5
TITLE: IR-5 Incident Monitoring
STATEMENT: >>>
Track and document incidents.
<<<
COMMENT: Baselines: Low, Moderate, High, Privacy
BASELINE: Low
STATUS: Draft

[REQUIREMENT]
UID: IR-5.1
TITLE: IR-5(1) Automated Tracking, Data Collection, and Analysis
STATEMENT: >>>
Track incidents and collect and analyze incident information using [organization-defined automated mechanisms].
<<<
COMMENT: Baselines: High
BASELINE: High
STATUS: Draft

[REQUIREMENT]
UID: IR-6
TITLE: IR-6 Incident Reporting
STATEMENT: >>>
a. Require personnel to report suspected incidents to the organizational incident response capability within [time period] ; and

b. Report incident information to [authorities].
<<<
COMMENT: Baselines: Low, Moderate, High, Privacy
BASELINE: Low
STATUS: Draft

[REQUIREMENT]
UID: IR-6.1
TITLE: IR-6(1) Automated Reporting
STATEMENT: >>>
Report incidents using [automated mechanisms].
<<<
COMMENT: Baselines: Moderate, High
BASELINE: Moderate
STATUS: Draft

[REQUIREMENT]
UID: IR-6.2
TITLE: IR-6(2) Vulnerabilities Related to Incidents
STATEMENT: >>>
Report system vulnerabilities associated with reported incidents to [personnel or roles].
<<<
BASELINE: None
STATUS: Draft

[REQUIREMENT]
UID: IR-6.3
TITLE: IR-6(3) Supply Chain Coordination
STATEMENT: >>>
Provide incident information to the provider of the product or service and other organizations involved in the supply chain or supply chain governance for systems or system components related to the incident.
<<<
COMMENT: Baselines: Moderate, High
BASELINE: Moderate
STATUS: Draft

[REQUIREMENT]
UID: IR-7
TITLE: IR-7 Incident Response Assistance
STATEMENT: >>>
Provide an incident response support resource, integral to the organizational incident response capability, that offers advice and assistance to users of the system for the handling and reporting of incidents.
<<<
COMMENT: Baselines: Low, Moderate, High, Privacy
BASELINE: Low
STATUS: Draft

[REQUIREMENT]
UID: IR-7.1
TITLE: IR-7(1) Automation Support for Availability of Information and Support
STATEMENT: >>>
Increase the availability of incident response information and support using [automated mechanisms].
<<<
COMMENT: Baselines: Moderate, High
BASELINE: Moderate
STATUS: Draft

[REQUIREMENT]
UID: IR-7.2
TITLE: IR-7(2) Coordination with External Providers
STATEMENT: >>>
(a) Establish a direct, cooperative relationship between its incident response capability and external providers of system protection capability; and

(b) Identify organizational incident response team members to the external providers.
<<<
BASELINE: None
STATUS: Draft

[REQUIREMENT]
UID: IR-8
TITLE: IR-8 Incident Response Plan
STATEMENT: >>>
a. Develop an incident response plan that:

  1. Provides the organization with a roadmap for implementing its incident response capability;

  2. Describes the structure and organization of the incident response capability;

  3. Provides a high-level approach for how the incident response capability fits into the overall organization;

  4. Meets the unique requirements of the organization, which relate to mission, size, structure, and functions;

  5. Defines reportable incidents;

  6. Provides metrics for measuring the incident response capability within the organization;

  7. Defines the resources and management support needed to effectively maintain and mature an incident response capability;

  8. Addresses the sharing of incident information;

  9. Is reviewed and approved by [personnel or roles] [frequency] ; and

  10. Explicitly designates responsibility for incident response to [entities, personnel, or roles].

b. Distribute copies of the incident response plan to [incident response personnel];

c. Update the incident response plan to address system and organizational changes or problems encountered during plan implementation, execution, or testing;

d. Communicate incident response plan changes to [organization-defined incident response personnel (identified by name and/or by role) and organizational elements] ; and

e. Protect the incident response plan from unauthorized disclosure and modification.
<<<
COMMENT: Baselines: Low, Moderate, High, Privacy
BASELINE: Low
STATUS: Draft

[REQUIREMENT]
UID: IR-8.1
TITLE: IR-8(1) Breaches
STATEMENT: >>>
Include the following in the Incident Response Plan for breaches involving personally identifiable information:

  (a) A process to determine if notice to individuals or other organizations, including oversight organizations, is needed;

  (b) An assessment process to determine the extent of the harm, embarrassment, inconvenience, or unfairness to affected individuals and any mechanisms to mitigate such harms; and

  (c) Identification of applicable privacy requirements.
<<<
COMMENT: Baselines: Privacy
BASELINE: Privacy
STATUS: Draft

[REQUIREMENT]
UID: IR-9
TITLE: IR-9 Information Spillage Response
STATEMENT: >>>
Respond to information spills by:

  a. Assigning [personnel or roles] with responsibility for responding to information spills;

  b. Identifying the specific information involved in the system contamination;

  c. Alerting [personnel or roles] of the information spill using a method of communication not associated with the spill;

  d. Isolating the contaminated system or system component;

  e. Eradicating the information from the contaminated system or component;

  f. Identifying other systems or system components that may have been subsequently contaminated; and

  g. Performing the following additional actions: [actions].
<<<
BASELINE: None
STATUS: Draft

[REQUIREMENT]
UID: IR-9.1
TITLE: IR-9(1) Responsible Personnel
STATEMENT: >>>
Withdrawn. Incorporated into IR-9.
<<<
COMMENT: Withdrawn
BASELINE: None
STATUS: Draft

[REQUIREMENT]
UID: IR-9.2
TITLE: IR-9(2) Training
STATEMENT: >>>
Provide information spillage response training [frequency].
<<<
BASELINE: None
STATUS: Draft

[REQUIREMENT]
UID: IR-9.3
TITLE: IR-9(3) Post-spill Operations
STATEMENT: >>>
Implement the following procedures to ensure that organizational personnel impacted by information spills can continue to carry out assigned tasks while contaminated systems are undergoing corrective actions: [procedures].
<<<
BASELINE: None
STATUS: Draft

[REQUIREMENT]
UID: IR-9.4
TITLE: IR-9(4) Exposure to Unauthorized Personnel
STATEMENT: >>>
Employ the following controls for personnel exposed to information not within assigned access authorizations: [controls].
<<<
BASELINE: None
STATUS: Draft

[REQUIREMENT]
UID: IR-10
TITLE: IR-10 Integrated Information Security Analysis Team
STATEMENT: >>>
Withdrawn.
<<<
COMMENT: Withdrawn
BASELINE: None
STATUS: Draft

[[/SECTION]]

[[SECTION]]
UID: NIST-MA
TITLE: MA — Maintenance

[REQUIREMENT]
UID: MA-1
TITLE: MA-1 Policy and Procedures
STATEMENT: >>>
a. Develop, document, and disseminate to [organization-defined personnel or roles]:

  1. [ma-01_odp.03] maintenance policy that:

    (a) Addresses purpose, scope, roles, responsibilities, management commitment, coordination among organizational entities, and compliance; and

    (b) Is consistent with applicable laws, executive orders, directives, regulations, policies, standards, and guidelines; and

  2. Procedures to facilitate the implementation of the maintenance policy and the associated maintenance controls;

b. Designate an [official] to manage the development, documentation, and dissemination of the maintenance policy and procedures; and

c. Review and update the current maintenance:

  1. Policy [frequency] and following [events] ; and

  2. Procedures [frequency] and following [events].
<<<
COMMENT: Baselines: Low, Moderate, High
BASELINE: Low
STATUS: Draft

[REQUIREMENT]
UID: MA-2
TITLE: MA-2 Controlled Maintenance
STATEMENT: >>>
a. Schedule, document, and review records of maintenance, repair, and replacement on system components in accordance with manufacturer or vendor specifications and/or organizational requirements;

b. Approve and monitor all maintenance activities, whether performed on site or remotely and whether the system or system components are serviced on site or removed to another location;

c. Require that [personnel or roles] explicitly approve the removal of the system or system components from organizational facilities for off-site maintenance, repair, or replacement;

d. Sanitize equipment to remove the following information from associated media prior to removal from organizational facilities for off-site maintenance, repair, or replacement: [information];

e. Check all potentially impacted controls to verify that the controls are still functioning properly following maintenance, repair, or replacement actions; and

f. Include the following information in organizational maintenance records: [information].
<<<
COMMENT: Baselines: Low, Moderate, High
BASELINE: Low
STATUS: Draft

[REQUIREMENT]
UID: MA-2.1
TITLE: MA-2(1) Record Content
STATEMENT: >>>
Withdrawn. Incorporated into MA-2.
<<<
COMMENT: Withdrawn
BASELINE: None
STATUS: Draft

[REQUIREMENT]
UID: MA-2.2
TITLE: MA-2(2) Automated Maintenance Activities
STATEMENT: >>>
(a) Schedule, conduct, and document maintenance, repair, and replacement actions for the system using [organization-defined automated mechanisms] ; and

(b) Produce up-to date, accurate, and complete records of all maintenance, repair, and replacement actions requested, scheduled, in process, and completed.
<<<
COMMENT: Baselines: High
BASELINE: High
STATUS: Draft

[REQUIREMENT]
UID: MA-3
TITLE: MA-3 Maintenance Tools
STATEMENT: >>>
a. Approve, control, and monitor the use of system maintenance tools; and

b. Review previously approved system maintenance tools [frequency].
<<<
COMMENT: Baselines: Moderate, High
BASELINE: Moderate
STATUS: Draft

[REQUIREMENT]
UID: MA-3.1
TITLE: MA-3(1) Inspect Tools
STATEMENT: >>>
Inspect the maintenance tools used by maintenance personnel for improper or unauthorized modifications.
<<<
COMMENT: Baselines: Moderate, High
BASELINE: Moderate
STATUS: Draft

[REQUIREMENT]
UID: MA-3.2
TITLE: MA-3(2) Inspect Media
STATEMENT: >>>
Check media containing diagnostic and test programs for malicious code before the media are used in the system.
<<<
COMMENT: Baselines: Moderate, High
BASELINE: Moderate
STATUS: Draft

[REQUIREMENT]
UID: MA-3.3
TITLE: MA-3(3) Prevent Unauthorized Removal
STATEMENT: >>>
Prevent the removal of maintenance equipment containing organizational information by:

  (a) Verifying that there is no organizational information contained on the equipment;

  (b) Sanitizing or destroying the equipment;

  (c) Retaining the equipment within the facility; or

  (d) Obtaining an exemption from [personnel or roles] explicitly authorizing removal of the equipment from the facility.
<<<
COMMENT: Baselines: Moderate, High
BASELINE: Moderate
STATUS: Draft

[REQUIREMENT]
UID: MA-3.4
TITLE: MA-3(4) Restricted Tool Use
STATEMENT: >>>
Restrict the use of maintenance tools to authorized personnel only.
<<<
BASELINE: None
STATUS: Draft

[REQUIREMENT]
UID: MA-3.5
TITLE: MA-3(5) Execution with Privilege
STATEMENT: >>>
Monitor the use of maintenance tools that execute with increased privilege.
<<<
BASELINE: None
STATUS: Draft

[REQUIREMENT]
UID: MA-3.6
TITLE: MA-3(6) Software Updates and Patches
STATEMENT: >>>
Inspect maintenance tools to ensure the latest software updates and patches are installed.
<<<
BASELINE: None
STATUS: Draft

[REQUIREMENT]
UID: MA-4
TITLE: MA-4 Nonlocal Maintenance
STATEMENT: >>>
a. Approve and monitor nonlocal maintenance and diagnostic activities;

b. Allow the use of nonlocal maintenance and diagnostic tools only as consistent with organizational policy and documented in the security plan for the system;

c. Employ strong authentication in the establishment of nonlocal maintenance and diagnostic sessions;

d. Maintain records for nonlocal maintenance and diagnostic activities; and

e. Terminate session and network connections when nonlocal maintenance is completed.
<<<
COMMENT: Baselines: Low, Moderate, High
BASELINE: Low
STATUS: Draft

[REQUIREMENT]
UID: MA-4.1
TITLE: MA-4(1) Logging and Review
STATEMENT: >>>
(a) Log [organization-defined audit events] for nonlocal maintenance and diagnostic sessions; and

(b) Review the audit records of the maintenance and diagnostic sessions to detect anomalous behavior.
<<<
BASELINE: None
STATUS: Draft

[REQUIREMENT]
UID: MA-4.2
TITLE: MA-4(2) Document Nonlocal Maintenance
STATEMENT: >>>
Withdrawn. Incorporated into MA-1, MA-4.
<<<
COMMENT: Withdrawn
BASELINE: None
STATUS: Draft

[REQUIREMENT]
UID: MA-4.3
TITLE: MA-4(3) Comparable Security and Sanitization
STATEMENT: >>>
(a) Require that nonlocal maintenance and diagnostic services be performed from a system that implements a security capability comparable to the capability implemented on the system being serviced; or

(b) Remove the component to be serviced from the system prior to nonlocal maintenance or diagnostic services; sanitize the component (for organizational information); and after the service is performed, inspect and sanitize the component (for potentially malicious software) before reconnecting the component to the system.
<<<
COMMENT: Baselines: High
BASELINE: High
STATUS: Draft

[REQUIREMENT]
UID: MA-4.4
TITLE: MA-4(4) Authentication and Separation of Maintenance Sessions
STATEMENT: >>>
Protect nonlocal maintenance sessions by:

  (a) Employing [authenticators that are replay resistant] ; and

  (b) Separating the maintenance sessions from other network sessions with the system by either:

    (1) Physically separated communications paths; or

    (2) Logically separated communications paths.
<<<
BASELINE: None
STATUS: Draft

[REQUIREMENT]
UID: MA-4.5
TITLE: MA-4(5) Approvals and Notifications
STATEMENT: >>>
(a) Require the approval of each nonlocal maintenance session by [personnel or roles] ; and

(b) Notify the following personnel or roles of the date and time of planned nonlocal maintenance: [personnel and roles].
<<<
BASELINE: None
STATUS: Draft

[REQUIREMENT]
UID: MA-4.6
TITLE: MA-4(6) Cryptographic Protection
STATEMENT: >>>
Implement the following cryptographic mechanisms to protect the integrity and confidentiality of nonlocal maintenance and diagnostic communications: [cryptographic mechanisms].
<<<
BASELINE: None
STATUS: Draft

[REQUIREMENT]
UID: MA-4.7
TITLE: MA-4(7) Disconnect Verification
STATEMENT: >>>
Verify session and network connection termination after the completion of nonlocal maintenance and diagnostic sessions.
<<<
BASELINE: None
STATUS: Draft

[REQUIREMENT]
UID: MA-5
TITLE: MA-5 Maintenance Personnel
STATEMENT: >>>
a. Establish a process for maintenance personnel authorization and maintain a list of authorized maintenance organizations or personnel;

b. Verify that non-escorted personnel performing maintenance on the system possess the required access authorizations; and

c. Designate organizational personnel with required access authorizations and technical competence to supervise the maintenance activities of personnel who do not possess the required access authorizations.
<<<
COMMENT: Baselines: Low, Moderate, High
BASELINE: Low
STATUS: Draft

[REQUIREMENT]
UID: MA-5.1
TITLE: MA-5(1) Individuals Without Appropriate Access
STATEMENT: >>>
(a) Implement procedures for the use of maintenance personnel that lack appropriate security clearances or are not U.S. citizens, that include the following requirements:

  (1) Maintenance personnel who do not have needed access authorizations, clearances, or formal access approvals are escorted and supervised during the performance of maintenance and diagnostic activities on the system by approved organizational personnel who are fully cleared, have appropriate access authorizations, and are technically qualified; and

  (2) Prior to initiating maintenance or diagnostic activities by personnel who do not have needed access authorizations, clearances or formal access approvals, all volatile information storage components within the system are sanitized and all nonvolatile storage media are removed or physically disconnected from the system and secured; and

(b) Develop and implement [alternate controls] in the event a system component cannot be sanitized, removed, or disconnected from the system.
<<<
COMMENT: Baselines: High
BASELINE: High
STATUS: Draft

[REQUIREMENT]
UID: MA-5.2
TITLE: MA-5(2) Security Clearances for Classified Systems
STATEMENT: >>>
Verify that personnel performing maintenance and diagnostic activities on a system processing, storing, or transmitting classified information possess security clearances and formal access approvals for at least the highest classification level and for compartments of information on the system.
<<<
BASELINE: None
STATUS: Draft

[REQUIREMENT]
UID: MA-5.3
TITLE: MA-5(3) Citizenship Requirements for Classified Systems
STATEMENT: >>>
Verify that personnel performing maintenance and diagnostic activities on a system processing, storing, or transmitting classified information are U.S. citizens.
<<<
BASELINE: None
STATUS: Draft

[REQUIREMENT]
UID: MA-5.4
TITLE: MA-5(4) Foreign Nationals
STATEMENT: >>>
Ensure that:

  (a) Foreign nationals with appropriate security clearances are used to conduct maintenance and diagnostic activities on classified systems only when the systems are jointly owned and operated by the United States and foreign allied governments, or owned and operated solely by foreign allied governments; and

  (b) Approvals, consents, and detailed operational conditions regarding the use of foreign nationals to conduct maintenance and diagnostic activities on classified systems are fully documented within Memoranda of Agreements.
<<<
BASELINE: None
STATUS: Draft

[REQUIREMENT]
UID: MA-5.5
TITLE: MA-5(5) Non-system Maintenance
STATEMENT: >>>
Ensure that non-escorted personnel performing maintenance activities not directly associated with the system but in the physical proximity of the system, have required access authorizations.
<<<
BASELINE: None
STATUS: Draft

[REQUIREMENT]
UID: MA-6
TITLE: MA-6 Timely Maintenance
STATEMENT: >>>
Obtain maintenance support and/or spare parts for [system components] within [time period] of failure.
<<<
COMMENT: Baselines: Moderate, High
BASELINE: Moderate
STATUS: Draft

[REQUIREMENT]
UID: MA-6.1
TITLE: MA-6(1) Preventive Maintenance
STATEMENT: >>>
Perform preventive maintenance on [system components] at [time intervals].
<<<
BASELINE: None
STATUS: Draft

[REQUIREMENT]
UID: MA-6.2
TITLE: MA-6(2) Predictive Maintenance
STATEMENT: >>>
Perform predictive maintenance on [system components] at [time intervals].
<<<
BASELINE: None
STATUS: Draft

[REQUIREMENT]
UID: MA-6.3
TITLE: MA-6(3) Automated Support for Predictive Maintenance
STATEMENT: >>>
Transfer predictive maintenance data to a maintenance management system using [automated mechanisms].
<<<
BASELINE: None
STATUS: Draft

[REQUIREMENT]
UID: MA-7
TITLE: MA-7 Field Maintenance
STATEMENT: >>>
Restrict or prohibit field maintenance on [systems or system components] to [trusted maintenance facilities].
<<<
BASELINE: None
STATUS: Draft

[[/SECTION]]

[[SECTION]]
UID: NIST-MP
TITLE: MP — Media Protection

[REQUIREMENT]
UID: MP-1
TITLE: MP-1 Policy and Procedures
STATEMENT: >>>
a. Develop, document, and disseminate to [organization-defined personnel or roles]:

  1. [mp-01_odp.03] media protection policy that:

    (a) Addresses purpose, scope, roles, responsibilities, management commitment, coordination among organizational entities, and compliance; and

    (b) Is consistent with applicable laws, executive orders, directives, regulations, policies, standards, and guidelines; and

  2. Procedures to facilitate the implementation of the media protection policy and the associated media protection controls;

b. Designate an [official] to manage the development, documentation, and dissemination of the media protection policy and procedures; and

c. Review and update the current media protection:

  1. Policy [frequency] and following [events] ; and

  2. Procedures [frequency] and following [events].
<<<
COMMENT: Baselines: Low, Moderate, High, Privacy
BASELINE: Low
STATUS: Draft

[REQUIREMENT]
UID: MP-2
TITLE: MP-2 Media Access
STATEMENT: >>>
Restrict access to [organization-defined types of digital and/or non-digital media] to [organization-defined personnel or roles].
<<<
COMMENT: Baselines: Low, Moderate, High
BASELINE: Low
STATUS: Draft

[REQUIREMENT]
UID: MP-2.1
TITLE: MP-2(1) Automated Restricted Access
STATEMENT: >>>
Withdrawn. Incorporated into MP-4.2.
<<<
COMMENT: Withdrawn
BASELINE: None
STATUS: Draft

[REQUIREMENT]
UID: MP-2.2
TITLE: MP-2(2) Cryptographic Protection
STATEMENT: >>>
Withdrawn. Incorporated into SC-28.1.
<<<
COMMENT: Withdrawn
BASELINE: None
STATUS: Draft

[REQUIREMENT]
UID: MP-3
TITLE: MP-3 Media Marking
STATEMENT: >>>
a. Mark system media indicating the distribution limitations, handling caveats, and applicable security markings (if any) of the information; and

b. Exempt [types of media exempted from marking] from marking if the media remain within [controlled areas].
<<<
COMMENT: Baselines: Moderate, High
BASELINE: Moderate
STATUS: Draft

[REQUIREMENT]
UID: MP-4
TITLE: MP-4 Media Storage
STATEMENT: >>>
a. Physically control and securely store [organization-defined types of digital and/or non-digital media] within [organization-defined controlled areas] ; and

b. Protect system media types defined in MP-4a until the media are destroyed or sanitized using approved equipment, techniques, and procedures.
<<<
COMMENT: Baselines: Moderate, High
BASELINE: Moderate
STATUS: Draft

[REQUIREMENT]
UID: MP-4.1
TITLE: MP-4(1) Cryptographic Protection
STATEMENT: >>>
Withdrawn. Incorporated into SC-28.1.
<<<
COMMENT: Withdrawn
BASELINE: None
STATUS: Draft

[REQUIREMENT]
UID: MP-4.2
TITLE: MP-4(2) Automated Restricted Access
STATEMENT: >>>
Restrict access to media storage areas and log access attempts and access granted using [organization-defined automated mechanisms].
<<<
BASELINE: None
STATUS: Draft

[REQUIREMENT]
UID: MP-5
TITLE: MP-5 Media Transport
STATEMENT: >>>
a. Protect and control [types of system media] during transport outside of controlled areas using [organization-defined controls];

b. Maintain accountability for system media during transport outside of controlled areas;

c. Document activities associated with the transport of system media; and

d. Restrict the activities associated with the transport of system media to authorized personnel.
<<<
COMMENT: Baselines: Moderate, High
BASELINE: Moderate
STATUS: Draft

[REQUIREMENT]
UID: MP-5.1
TITLE: MP-5(1) Protection Outside of Controlled Areas
STATEMENT: >>>
Withdrawn. Incorporated into MP-5.
<<<
COMMENT: Withdrawn
BASELINE: None
STATUS: Draft

[REQUIREMENT]
UID: MP-5.2
TITLE: MP-5(2) Documentation of Activities
STATEMENT: >>>
Withdrawn. Incorporated into MP-5.
<<<
COMMENT: Withdrawn
BASELINE: None
STATUS: Draft

[REQUIREMENT]
UID: MP-5.3
TITLE: MP-5(3) Custodians
STATEMENT: >>>
Employ an identified custodian during transport of system media outside of controlled areas.
<<<
BASELINE: None
STATUS: Draft

[REQUIREMENT]
UID: MP-5.4
TITLE: MP-5(4) Cryptographic Protection
STATEMENT: >>>
Withdrawn. Incorporated into SC-28.1.
<<<
COMMENT: Withdrawn
BASELINE: None
STATUS: Draft

[REQUIREMENT]
UID: MP-6
TITLE: MP-6 Media Sanitization
STATEMENT: >>>
a. Sanitize [organization-defined system media] prior to disposal, release out of organizational control, or release for reuse using [organization-defined sanitization techniques and procedures] ; and

b. Employ sanitization mechanisms with the strength and integrity commensurate with the security category or classification of the information.
<<<
COMMENT: Baselines: Low, Moderate, High, Privacy
BASELINE: Low
STATUS: Draft

[REQUIREMENT]
UID: MP-6.1
TITLE: MP-6(1) Review, Approve, Track, Document, and Verify
STATEMENT: >>>
Review, approve, track, document, and verify media sanitization and disposal actions.
<<<
COMMENT: Baselines: High
BASELINE: High
STATUS: Draft

[REQUIREMENT]
UID: MP-6.2
TITLE: MP-6(2) Equipment Testing
STATEMENT: >>>
Test sanitization equipment and procedures [organization-defined frequency] to ensure that the intended sanitization is being achieved.
<<<
COMMENT: Baselines: High
BASELINE: High
STATUS: Draft

[REQUIREMENT]
UID: MP-6.3
TITLE: MP-6(3) Nondestructive Techniques
STATEMENT: >>>
Apply nondestructive sanitization techniques to portable storage devices prior to connecting such devices to the system under the following circumstances: [circumstances].
<<<
COMMENT: Baselines: High
BASELINE: High
STATUS: Draft

[REQUIREMENT]
UID: MP-6.4
TITLE: MP-6(4) Controlled Unclassified Information
STATEMENT: >>>
Withdrawn. Incorporated into MP-6.
<<<
COMMENT: Withdrawn
BASELINE: None
STATUS: Draft

[REQUIREMENT]
UID: MP-6.5
TITLE: MP-6(5) Classified Information
STATEMENT: >>>
Withdrawn. Incorporated into MP-6.
<<<
COMMENT: Withdrawn
BASELINE: None
STATUS: Draft

[REQUIREMENT]
UID: MP-6.6
TITLE: MP-6(6) Media Destruction
STATEMENT: >>>
Withdrawn. Incorporated into MP-6.
<<<
COMMENT: Withdrawn
BASELINE: None
STATUS: Draft

[REQUIREMENT]
UID: MP-6.7
TITLE: MP-6(7) Dual Authorization
STATEMENT: >>>
Enforce dual authorization for the sanitization of [system media].
<<<
BASELINE: None
STATUS: Draft

[REQUIREMENT]
UID: MP-6.8
TITLE: MP-6(8) Remote Purging or Wiping of Information
STATEMENT: >>>
Provide the capability to purge or wipe information from [systems or system components] [mp-06.08_odp.02].
<<<
BASELINE: None
STATUS: Draft

[REQUIREMENT]
UID: MP-7
TITLE: MP-7 Media Use
STATEMENT: >>>
a. [mp-07_odp.02] the use of [types of system media] on [systems or system components] using [controls] ; and

b. Prohibit the use of portable storage devices in organizational systems when such devices have no identifiable owner.
<<<
COMMENT: Baselines: Low, Moderate, High
BASELINE: Low
STATUS: Draft

[REQUIREMENT]
UID: MP-7.1
TITLE: MP-7(1) Prohibit Use Without Owner
STATEMENT: >>>
Withdrawn. Incorporated into MP-7.
<<<
COMMENT: Withdrawn
BASELINE: None
STATUS: Draft

[REQUIREMENT]
UID: MP-7.2
TITLE: MP-7(2) Prohibit Use of Sanitization-resistant Media
STATEMENT: >>>
Prohibit the use of sanitization-resistant media in organizational systems.
<<<
BASELINE: None
STATUS: Draft

[REQUIREMENT]
UID: MP-8
TITLE: MP-8 Media Downgrading
STATEMENT: >>>
a. Establish [system media downgrading process] that includes employing downgrading mechanisms with strength and integrity commensurate with the security category or classification of the information;

b. Verify that the system media downgrading process is commensurate with the security category and/or classification level of the information to be removed and the access authorizations of the potential recipients of the downgraded information;

c. Identify [system media requiring downgrading] ; and

d. Downgrade the identified system media using the established process.
<<<
BASELINE: None
STATUS: Draft

[REQUIREMENT]
UID: MP-8.1
TITLE: MP-8(1) Documentation of Process
STATEMENT: >>>
Document system media downgrading actions.
<<<
BASELINE: None
STATUS: Draft

[REQUIREMENT]
UID: MP-8.2
TITLE: MP-8(2) Equipment Testing
STATEMENT: >>>
Test downgrading equipment and procedures [organization-defined frequency] to ensure that downgrading actions are being achieved.
<<<
BASELINE: None
STATUS: Draft

[REQUIREMENT]
UID: MP-8.3
TITLE: MP-8(3) Controlled Unclassified Information
STATEMENT: >>>
Downgrade system media containing controlled unclassified information prior to public release.
<<<
BASELINE: None
STATUS: Draft

[REQUIREMENT]
UID: MP-8.4
TITLE: MP-8(4) Classified Information
STATEMENT: >>>
Downgrade system media containing classified information prior to release to individuals without required access authorizations.
<<<
BASELINE: None
STATUS: Draft

[[/SECTION]]

[[SECTION]]
UID: NIST-PE
TITLE: PE — Physical and Environmental Protection

[REQUIREMENT]
UID: PE-1
TITLE: PE-1 Policy and Procedures
STATEMENT: >>>
a. Develop, document, and disseminate to [organization-defined personnel or roles]:

  1. [pe-01_odp.03] physical and environmental protection policy that:

    (a) Addresses purpose, scope, roles, responsibilities, management commitment, coordination among organizational entities, and compliance; and

    (b) Is consistent with applicable laws, executive orders, directives, regulations, policies, standards, and guidelines; and

  2. Procedures to facilitate the implementation of the physical and environmental protection policy and the associated physical and environmental protection controls;

b. Designate an [official] to manage the development, documentation, and dissemination of the physical and environmental protection policy and procedures; and

c. Review and update the current physical and environmental protection:

  1. Policy [frequency] and following [events] ; and

  2. Procedures [frequency] and following [events].
<<<
COMMENT: Baselines: Low, Moderate, High
BASELINE: Low
STATUS: Draft

[REQUIREMENT]
UID: PE-2
TITLE: PE-2 Physical Access Authorizations
STATEMENT: >>>
a. Develop, approve, and maintain a list of individuals with authorized access to the facility where the system resides;

b. Issue authorization credentials for facility access;

c. Review the access list detailing authorized facility access by individuals [frequency] ; and

d. Remove individuals from the facility access list when access is no longer required.
<<<
COMMENT: Baselines: Low, Moderate, High
BASELINE: Low
STATUS: Draft

[REQUIREMENT]
UID: PE-2.1
TITLE: PE-2(1) Access by Position or Role
STATEMENT: >>>
Authorize physical access to the facility where the system resides based on position or role.
<<<
BASELINE: None
STATUS: Draft

[REQUIREMENT]
UID: PE-2.2
TITLE: PE-2(2) Two Forms of Identification
STATEMENT: >>>
Require two forms of identification from the following forms of identification for visitor access to the facility where the system resides: [list of acceptable forms of identification].
<<<
BASELINE: None
STATUS: Draft

[REQUIREMENT]
UID: PE-2.3
TITLE: PE-2(3) Restrict Unescorted Access
STATEMENT: >>>
Restrict unescorted access to the facility where the system resides to personnel with [pe-02.03_odp.01].
<<<
BASELINE: None
STATUS: Draft

[REQUIREMENT]
UID: PE-3
TITLE: PE-3 Physical Access Control
STATEMENT: >>>
a. Enforce physical access authorizations at [entry and exit points] by:

  1. Verifying individual access authorizations before granting access to the facility; and

  2. Controlling ingress and egress to the facility using [pe-03_odp.02];

b. Maintain physical access audit logs for [entry or exit points];

c. Control access to areas within the facility designated as publicly accessible by implementing the following controls: [physical access controls];

d. Escort visitors and control visitor activity [circumstances];

e. Secure keys, combinations, and other physical access devices;

f. Inventory [physical access devices] every [frequency] ; and

g. Change combinations and keys [organization-defined frequency] and/or when keys are lost, combinations are compromised, or when individuals possessing the keys or combinations are transferred or terminated.
<<<
COMMENT: Baselines: Low, Moderate, High
BASELINE: Low
STATUS: Draft

[REQUIREMENT]
UID: PE-3.1
TITLE: PE-3(1) System Access
STATEMENT: >>>
Enforce physical access authorizations to the system in addition to the physical access controls for the facility at [physical spaces].
<<<
COMMENT: Baselines: High
BASELINE: High
STATUS: Draft

[REQUIREMENT]
UID: PE-3.2
TITLE: PE-3(2) Facility and Systems
STATEMENT: >>>
Perform security checks [frequency] at the physical perimeter of the facility or system for exfiltration of information or removal of system components.
<<<
BASELINE: None
STATUS: Draft

[REQUIREMENT]
UID: PE-3.3
TITLE: PE-3(3) Continuous Guards
STATEMENT: >>>
Employ guards to control [physical access points] to the facility where the system resides 24 hours per day, 7 days per week.
<<<
BASELINE: None
STATUS: Draft

[REQUIREMENT]
UID: PE-3.4
TITLE: PE-3(4) Lockable Casings
STATEMENT: >>>
Use lockable physical casings to protect [system components] from unauthorized physical access.
<<<
BASELINE: None
STATUS: Draft

[REQUIREMENT]
UID: PE-3.5
TITLE: PE-3(5) Tamper Protection
STATEMENT: >>>
Employ [anti-tamper technologies] to [pe-03.05_odp.02] physical tampering or alteration of [hardware components] within the system.
<<<
BASELINE: None
STATUS: Draft

[REQUIREMENT]
UID: PE-3.6
TITLE: PE-3(6) Facility Penetration Testing
STATEMENT: >>>
Withdrawn. Incorporated into CA-8.
<<<
COMMENT: Withdrawn
BASELINE: None
STATUS: Draft

[REQUIREMENT]
UID: PE-3.7
TITLE: PE-3(7) Physical Barriers
STATEMENT: >>>
Limit access using physical barriers.
<<<
BASELINE: None
STATUS: Draft

[REQUIREMENT]
UID: PE-3.8
TITLE: PE-3(8) Access Control Vestibules
STATEMENT: >>>
Employ access control vestibules at [locations].
<<<
BASELINE: None
STATUS: Draft

[REQUIREMENT]
UID: PE-4
TITLE: PE-4 Access Control for Transmission
STATEMENT: >>>
Control physical access to [system distribution and transmission lines] within organizational facilities using [security controls].
<<<
COMMENT: Baselines: Moderate, High
BASELINE: Moderate
STATUS: Draft

[REQUIREMENT]
UID: PE-5
TITLE: PE-5 Access Control for Output Devices
STATEMENT: >>>
Control physical access to output from [output devices] to prevent unauthorized individuals from obtaining the output.
<<<
COMMENT: Baselines: Moderate, High
BASELINE: Moderate
STATUS: Draft

[REQUIREMENT]
UID: PE-5.1
TITLE: PE-5(1) Access to Output by Authorized Individuals
STATEMENT: >>>
Withdrawn. Incorporated into PE-5.
<<<
COMMENT: Withdrawn
BASELINE: None
STATUS: Draft

[REQUIREMENT]
UID: PE-5.2
TITLE: PE-5(2) Link to Individual Identity
STATEMENT: >>>
Link individual identity to receipt of output from output devices.
<<<
BASELINE: None
STATUS: Draft

[REQUIREMENT]
UID: PE-5.3
TITLE: PE-5(3) Marking Output Devices
STATEMENT: >>>
Withdrawn. Incorporated into PE-22.
<<<
COMMENT: Withdrawn
BASELINE: None
STATUS: Draft

[REQUIREMENT]
UID: PE-6
TITLE: PE-6 Monitoring Physical Access
STATEMENT: >>>
a. Monitor physical access to the facility where the system resides to detect and respond to physical security incidents;

b. Review physical access logs [frequency] and upon occurrence of [events] ; and

c. Coordinate results of reviews and investigations with the organizational incident response capability.
<<<
COMMENT: Baselines: Low, Moderate, High
BASELINE: Low
STATUS: Draft

[REQUIREMENT]
UID: PE-6.1
TITLE: PE-6(1) Intrusion Alarms and Surveillance Equipment
STATEMENT: >>>
Monitor physical access to the facility where the system resides using physical intrusion alarms and surveillance equipment.
<<<
COMMENT: Baselines: Moderate, High
BASELINE: Moderate
STATUS: Draft

[REQUIREMENT]
UID: PE-6.2
TITLE: PE-6(2) Automated Intrusion Recognition and Responses
STATEMENT: >>>
Recognize [classes or types of intrusions] and initiate [response actions] using [automated mechanisms].
<<<
BASELINE: None
STATUS: Draft

[REQUIREMENT]
UID: PE-6.3
TITLE: PE-6(3) Video Surveillance
STATEMENT: >>>
(a) Employ video surveillance of [operational areas];

(b) Review video recordings [frequency] ; and

(c) Retain video recordings for [time period].
<<<
BASELINE: None
STATUS: Draft

[REQUIREMENT]
UID: PE-6.4
TITLE: PE-6(4) Monitoring Physical Access to Systems
STATEMENT: >>>
Monitor physical access to the system in addition to the physical access monitoring of the facility at [physical spaces].
<<<
COMMENT: Baselines: High
BASELINE: High
STATUS: Draft

[REQUIREMENT]
UID: PE-7
TITLE: PE-7 Visitor Control
STATEMENT: >>>
Withdrawn. Incorporated into PE-2, PE-3.
<<<
COMMENT: Withdrawn
BASELINE: None
STATUS: Draft

[REQUIREMENT]
UID: PE-8
TITLE: PE-8 Visitor Access Records
STATEMENT: >>>
a. Maintain visitor access records to the facility where the system resides for [time period];

b. Review visitor access records [frequency] ; and

c. Report anomalies in visitor access records to [personnel].
<<<
COMMENT: Baselines: Low, Moderate, High
BASELINE: Low
STATUS: Draft

[REQUIREMENT]
UID: PE-8.1
TITLE: PE-8(1) Automated Records Maintenance and Review
STATEMENT: >>>
Maintain and review visitor access records using [organization-defined automated mechanisms].
<<<
COMMENT: Baselines: High
BASELINE: High
STATUS: Draft

[REQUIREMENT]
UID: PE-8.2
TITLE: PE-8(2) Physical Access Records
STATEMENT: >>>
Withdrawn. Incorporated into PE-2.
<<<
COMMENT: Withdrawn
BASELINE: None
STATUS: Draft

[REQUIREMENT]
UID: PE-8.3
TITLE: PE-8(3) Limit Personally Identifiable Information Elements
STATEMENT: >>>
Limit personally identifiable information contained in visitor access records to the following elements identified in the privacy risk assessment: [elements].
<<<
COMMENT: Baselines: Privacy
BASELINE: Privacy
STATUS: Draft

[REQUIREMENT]
UID: PE-9
TITLE: PE-9 Power Equipment and Cabling
STATEMENT: >>>
Protect power equipment and power cabling for the system from damage and destruction.
<<<
COMMENT: Baselines: Moderate, High
BASELINE: Moderate
STATUS: Draft

[REQUIREMENT]
UID: PE-9.1
TITLE: PE-9(1) Redundant Cabling
STATEMENT: >>>
Employ redundant power cabling paths that are physically separated by [distance].
<<<
BASELINE: None
STATUS: Draft

[REQUIREMENT]
UID: PE-9.2
TITLE: PE-9(2) Automatic Voltage Controls
STATEMENT: >>>
Employ automatic voltage controls for [critical system components].
<<<
BASELINE: None
STATUS: Draft

[REQUIREMENT]
UID: PE-10
TITLE: PE-10 Emergency Shutoff
STATEMENT: >>>
a. Provide the capability of shutting off power to [system or individual system components] in emergency situations;

b. Place emergency shutoff switches or devices in [location] to facilitate access for authorized personnel; and

c. Protect emergency power shutoff capability from unauthorized activation.
<<<
COMMENT: Baselines: Moderate, High
BASELINE: Moderate
STATUS: Draft

[REQUIREMENT]
UID: PE-10.1
TITLE: PE-10(1) Accidental and Unauthorized Activation
STATEMENT: >>>
Withdrawn. Incorporated into PE-10.
<<<
COMMENT: Withdrawn
BASELINE: None
STATUS: Draft

[REQUIREMENT]
UID: PE-11
TITLE: PE-11 Emergency Power
STATEMENT: >>>
Provide an uninterruptible power supply to facilitate [pe-11_odp] in the event of a primary power source loss.
<<<
COMMENT: Baselines: Moderate, High
BASELINE: Moderate
STATUS: Draft

[REQUIREMENT]
UID: PE-11.1
TITLE: PE-11(1) Alternate Power Supply — Minimal Operational Capability
STATEMENT: >>>
Provide an alternate power supply for the system that is activated [pe-11.01_odp] and that can maintain minimally required operational capability in the event of an extended loss of the primary power source.
<<<
COMMENT: Baselines: High
BASELINE: High
STATUS: Draft

[REQUIREMENT]
UID: PE-11.2
TITLE: PE-11(2) Alternate Power Supply — Self-contained
STATEMENT: >>>
Provide an alternate power supply for the system that is activated [pe-11.02_odp.01] and that is:

  (a) Self-contained;

  (b) Not reliant on external power generation; and

  (c) Capable of maintaining [pe-11.02_odp.02] in the event of an extended loss of the primary power source.
<<<
BASELINE: None
STATUS: Draft

[REQUIREMENT]
UID: PE-12
TITLE: PE-12 Emergency Lighting
STATEMENT: >>>
Employ and maintain automatic emergency lighting for the system that activates in the event of a power outage or disruption and that covers emergency exits and evacuation routes within the facility.
<<<
COMMENT: Baselines: Low, Moderate, High
BASELINE: Low
STATUS: Draft

[REQUIREMENT]
UID: PE-12.1
TITLE: PE-12(1) Essential Mission and Business Functions
STATEMENT: >>>
Provide emergency lighting for all areas within the facility supporting essential mission and business functions.
<<<
BASELINE: None
STATUS: Draft

[REQUIREMENT]
UID: PE-13
TITLE: PE-13 Fire Protection
STATEMENT: >>>
Employ and maintain fire detection and suppression systems that are supported by an independent energy source.
<<<
COMMENT: Baselines: Low, Moderate, High
BASELINE: Low
STATUS: Draft

[REQUIREMENT]
UID: PE-13.1
TITLE: PE-13(1) Detection Systems — Automatic Activation and Notification
STATEMENT: >>>
Employ fire detection systems that activate automatically and notify [personnel or roles] and [emergency responders] in the event of a fire.
<<<
COMMENT: Baselines: Moderate, High
BASELINE: Moderate
STATUS: Draft

[REQUIREMENT]
UID: PE-13.2
TITLE: PE-13(2) Suppression Systems — Automatic Activation and Notification
STATEMENT: >>>
(a) Employ fire suppression systems that activate automatically and notify [personnel or roles] and [emergency responders] ; and

(b) Employ an automatic fire suppression capability when the facility is not staffed on a continuous basis.
<<<
COMMENT: Baselines: High
BASELINE: High
STATUS: Draft

[REQUIREMENT]
UID: PE-13.3
TITLE: PE-13(3) Automatic Fire Suppression
STATEMENT: >>>
Withdrawn. Incorporated into PE-13.2.
<<<
COMMENT: Withdrawn
BASELINE: None
STATUS: Draft

[REQUIREMENT]
UID: PE-13.4
TITLE: PE-13(4) Inspections
STATEMENT: >>>
Ensure that the facility undergoes [frequency] fire protection inspections by authorized and qualified inspectors and identified deficiencies are resolved within [time period].
<<<
BASELINE: None
STATUS: Draft

[REQUIREMENT]
UID: PE-14
TITLE: PE-14 Environmental Controls
STATEMENT: >>>
a. Maintain [pe-14_odp.01] levels within the facility where the system resides at [acceptable levels] ; and

b. Monitor environmental control levels [frequency].
<<<
COMMENT: Baselines: Low, Moderate, High
BASELINE: Low
STATUS: Draft

[REQUIREMENT]
UID: PE-14.1
TITLE: PE-14(1) Automatic Controls
STATEMENT: >>>
Employ the following automatic environmental controls in the facility to prevent fluctuations potentially harmful to the system: [automatic environmental controls].
<<<
BASELINE: None
STATUS: Draft

[REQUIREMENT]
UID: PE-14.2
TITLE: PE-14(2) Monitoring with Alarms and Notifications
STATEMENT: >>>
Employ environmental control monitoring that provides an alarm or notification of changes potentially harmful to personnel or equipment to [personnel or roles].
<<<
BASELINE: None
STATUS: Draft

[REQUIREMENT]
UID: PE-15
TITLE: PE-15 Water Damage Protection
STATEMENT: >>>
Protect the system from damage resulting from water leakage by providing master shutoff or isolation valves that are accessible, working properly, and known to key personnel.
<<<
COMMENT: Baselines: Low, Moderate, High
BASELINE: Low
STATUS: Draft

[REQUIREMENT]
UID: PE-15.1
TITLE: PE-15(1) Automation Support
STATEMENT: >>>
Detect the presence of water near the system and alert [personnel or roles] using [automated mechanisms].
<<<
COMMENT: Baselines: High
BASELINE: High
STATUS: Draft

[REQUIREMENT]
UID: PE-16
TITLE: PE-16 Delivery and Removal
STATEMENT: >>>
a. Authorize and control [organization-defined types of system components] entering and exiting the facility; and

b. Maintain records of the system components.
<<<
COMMENT: Baselines: Low, Moderate, High
BASELINE: Low
STATUS: Draft

[REQUIREMENT]
UID: PE-17
TITLE: PE-17 Alternate Work Site
STATEMENT: >>>
a. Determine and document the [alternate work sites] allowed for use by employees;

b. Employ the following controls at alternate work sites: [controls];

c. Assess the effectiveness of controls at alternate work sites; and

d. Provide a means for employees to communicate with information security and privacy personnel in case of incidents.
<<<
COMMENT: Baselines: Moderate, High
BASELINE: Moderate
STATUS: Draft

[REQUIREMENT]
UID: PE-18
TITLE: PE-18 Location of System Components
STATEMENT: >>>
Position system components within the facility to minimize potential damage from [physical and environmental hazards] and to minimize the opportunity for unauthorized access.
<<<
COMMENT: Baselines: High
BASELINE: High
STATUS: Draft

[REQUIREMENT]
UID: PE-18.1
TITLE: PE-18(1) Facility Site
STATEMENT: >>>
Withdrawn.
<<<
COMMENT: Withdrawn
BASELINE: None
STATUS: Draft

[REQUIREMENT]
UID: PE-19
TITLE: PE-19 Information Leakage
STATEMENT: >>>
Protect the system from information leakage due to electromagnetic signals emanations.
<<<
BASELINE: None
STATUS: Draft

[REQUIREMENT]
UID: PE-19.1
TITLE: PE-19(1) National Emissions Policies and Procedures
STATEMENT: >>>
Protect system components, associated data communications, and networks in accordance with national Emissions Security policies and procedures based on the security category or classification of the information.
<<<
BASELINE: None
STATUS: Draft

[REQUIREMENT]
UID: PE-20
TITLE: PE-20 Asset Monitoring and Tracking
STATEMENT: >>>
Employ [asset location technologies] to track and monitor the location and movement of [assets] within [controlled areas].
<<<
BASELINE: None
STATUS: Draft

[REQUIREMENT]
UID: PE-21
TITLE: PE-21 Electromagnetic Pulse Protection
STATEMENT: >>>
Employ [protective measures] against electromagnetic pulse damage for [system and system components].
<<<
BASELINE: None
STATUS: Draft

[REQUIREMENT]
UID: PE-22
TITLE: PE-22 Component Marking
STATEMENT: >>>
Mark [system hardware components] indicating the impact level or classification level of the information permitted to be processed, stored, or transmitted by the hardware component.
<<<
BASELINE: None
STATUS: Draft

[REQUIREMENT]
UID: PE-23
TITLE: PE-23 Facility Location
STATEMENT: >>>
a. Plan the location or site of the facility where the system resides considering physical and environmental hazards; and

b. For existing facilities, consider the physical and environmental hazards in the organizational risk management strategy.
<<<
BASELINE: None
STATUS: Draft

[[/SECTION]]

[[SECTION]]
UID: NIST-PL
TITLE: PL — Planning

[REQUIREMENT]
UID: PL-1
TITLE: PL-1 Policy and Procedures
STATEMENT: >>>
a. Develop, document, and disseminate to [organization-defined personnel or roles]:

  1. [pl-01_odp.03] planning policy that:

    (a) Addresses purpose, scope, roles, responsibilities, management commitment, coordination among organizational entities, and compliance; and

    (b) Is consistent with applicable laws, executive orders, directives, regulations, policies, standards, and guidelines; and

  2. Procedures to facilitate the implementation of the planning policy and the associated planning controls;

b. Designate an [official] to manage the development, documentation, and dissemination of the planning policy and procedures; and

c. Review and update the current planning:

  1. Policy [frequency] and following [events] ; and

  2. Procedures [frequency] and following [events].
<<<
COMMENT: Baselines: Low, Moderate, High, Privacy
BASELINE: Low
STATUS: Draft

[REQUIREMENT]
UID: PL-2
TITLE: PL-2 System Security and Privacy Plans
STATEMENT: >>>
a. Develop security and privacy plans for the system that:

  1. Are consistent with the organization’s enterprise architecture;

  2. Explicitly define the constituent system components;

  3. Describe the operational context of the system in terms of mission and business processes;

  4. Identify the individuals that fulfill system roles and responsibilities;

  5. Identify the information types processed, stored, and transmitted by the system;

  6. Provide the security categorization of the system, including supporting rationale;

  7. Describe any specific threats to the system that are of concern to the organization;

  8. Provide the results of a privacy risk assessment for systems processing personally identifiable information;

  9. Describe the operational environment for the system and any dependencies on or connections to other systems or system components;

  10. Provide an overview of the security and privacy requirements for the system;

  11. Identify any relevant control baselines or overlays, if applicable;

  12. Describe the controls in place or planned for meeting the security and privacy requirements, including a rationale for any tailoring decisions;

  13. Include risk determinations for security and privacy architecture and design decisions;

  14. Include security- and privacy-related activities affecting the system that require planning and coordination with [individuals or groups] ; and

  15. Are reviewed and approved by the authorizing official or designated representative prior to plan implementation.

b. Distribute copies of the plans and communicate subsequent changes to the plans to [personnel or roles];

c. Review the plans [frequency];

d. Update the plans to address changes to the system and environment of operation or problems identified during plan implementation or control assessments; and

e. Protect the plans from unauthorized disclosure and modification.
<<<
COMMENT: Baselines: Low, Moderate, High, Privacy
BASELINE: Low
STATUS: Draft

[REQUIREMENT]
UID: PL-2.1
TITLE: PL-2(1) Concept of Operations
STATEMENT: >>>
Withdrawn. Incorporated into PL-7.
<<<
COMMENT: Withdrawn
BASELINE: None
STATUS: Draft

[REQUIREMENT]
UID: PL-2.2
TITLE: PL-2(2) Functional Architecture
STATEMENT: >>>
Withdrawn. Incorporated into PL-8.
<<<
COMMENT: Withdrawn
BASELINE: None
STATUS: Draft

[REQUIREMENT]
UID: PL-2.3
TITLE: PL-2(3) Plan and Coordinate with Other Organizational Entities
STATEMENT: >>>
Withdrawn. Incorporated into PL-2.
<<<
COMMENT: Withdrawn
BASELINE: None
STATUS: Draft

[REQUIREMENT]
UID: PL-3
TITLE: PL-3 System Security Plan Update
STATEMENT: >>>
Withdrawn. Incorporated into PL-2.
<<<
COMMENT: Withdrawn
BASELINE: None
STATUS: Draft

[REQUIREMENT]
UID: PL-4
TITLE: PL-4 Rules of Behavior
STATEMENT: >>>
a. Establish and provide to individuals requiring access to the system, the rules that describe their responsibilities and expected behavior for information and system usage, security, and privacy;

b. Receive a documented acknowledgment from such individuals, indicating that they have read, understand, and agree to abide by the rules of behavior, before authorizing access to information and the system;

c. Review and update the rules of behavior [frequency] ; and

d. Require individuals who have acknowledged a previous version of the rules of behavior to read and re-acknowledge [pl-04_odp.02].
<<<
COMMENT: Baselines: Low, Moderate, High, Privacy
BASELINE: Low
STATUS: Draft

[REQUIREMENT]
UID: PL-4.1
TITLE: PL-4(1) Social Media and External Site/Application Usage Restrictions
STATEMENT: >>>
Include in the rules of behavior, restrictions on:

  (a) Use of social media, social networking sites, and external sites/applications;

  (b) Posting organizational information on public websites; and

  (c) Use of organization-provided identifiers (e.g., email addresses) and authentication secrets (e.g., passwords) for creating accounts on external sites/applications.
<<<
COMMENT: Baselines: Low, Moderate, High, Privacy
BASELINE: Low
STATUS: Draft

[REQUIREMENT]
UID: PL-5
TITLE: PL-5 Privacy Impact Assessment
STATEMENT: >>>
Withdrawn. Incorporated into RA-8.
<<<
COMMENT: Withdrawn
BASELINE: None
STATUS: Draft

[REQUIREMENT]
UID: PL-6
TITLE: PL-6 Security-related Activity Planning
STATEMENT: >>>
Withdrawn. Incorporated into PL-2.
<<<
COMMENT: Withdrawn
BASELINE: None
STATUS: Draft

[REQUIREMENT]
UID: PL-7
TITLE: PL-7 Concept of Operations
STATEMENT: >>>
a. Develop a Concept of Operations (CONOPS) for the system describing how the organization intends to operate the system from the perspective of information security and privacy; and

b. Review and update the CONOPS [frequency].
<<<
BASELINE: None
STATUS: Draft

[REQUIREMENT]
UID: PL-8
TITLE: PL-8 Security and Privacy Architectures
STATEMENT: >>>
a. Develop security and privacy architectures for the system that:

  1. Describe the requirements and approach to be taken for protecting the confidentiality, integrity, and availability of organizational information;

  2. Describe the requirements and approach to be taken for processing personally identifiable information to minimize privacy risk to individuals;

  3. Describe how the architectures are integrated into and support the enterprise architecture; and

  4. Describe any assumptions about, and dependencies on, external systems and services;

b. Review and update the architectures [frequency] to reflect changes in the enterprise architecture; and

c. Reflect planned architecture changes in security and privacy plans, Concept of Operations (CONOPS), criticality analysis, organizational procedures, and procurements and acquisitions.
<<<
COMMENT: Baselines: Moderate, High, Privacy
BASELINE: Moderate
STATUS: Draft

[REQUIREMENT]
UID: PL-8.1
TITLE: PL-8(1) Defense in Depth
STATEMENT: >>>
Design the security and privacy architectures for the system using a defense-in-depth approach that:

  (a) Allocates [controls] to [locations and architectural layers] ; and

  (b) Ensures that the allocated controls operate in a coordinated and mutually reinforcing manner.
<<<
BASELINE: None
STATUS: Draft

[REQUIREMENT]
UID: PL-8.2
TITLE: PL-8(2) Supplier Diversity
STATEMENT: >>>
Require that [controls] allocated to [locations and architectural layers] are obtained from different suppliers.
<<<
BASELINE: None
STATUS: Draft

[REQUIREMENT]
UID: PL-9
TITLE: PL-9 Central Management
STATEMENT: >>>
Centrally manage [controls and related processes].
<<<
COMMENT: Baselines: Privacy
BASELINE: Privacy
STATUS: Draft

[REQUIREMENT]
UID: PL-10
TITLE: PL-10 Baseline Selection
STATEMENT: >>>
Select a control baseline for the system.
<<<
COMMENT: Baselines: Low, Moderate, High
BASELINE: Low
STATUS: Draft

[REQUIREMENT]
UID: PL-11
TITLE: PL-11 Baseline Tailoring
STATEMENT: >>>
Tailor the selected control baseline by applying specified tailoring actions.
<<<
COMMENT: Baselines: Low, Moderate, High
BASELINE: Low
STATUS: Draft

[[/SECTION]]

[[SECTION]]
UID: NIST-PM
TITLE: PM — Program Management

[REQUIREMENT]
UID: PM-1
TITLE: PM-1 Information Security Program Plan
STATEMENT: >>>
a. Develop and disseminate an organization-wide information security program plan that:

  1. Provides an overview of the requirements for the security program and a description of the security program management controls and common controls in place or planned for meeting those requirements;

  2. Includes the identification and assignment of roles, responsibilities, management commitment, coordination among organizational entities, and compliance;

  3. Reflects the coordination among organizational entities responsible for information security; and

  4. Is approved by a senior official with responsibility and accountability for the risk being incurred to organizational operations (including mission, functions, image, and reputation), organizational assets, individuals, other organizations, and the Nation;

b. Review and update the organization-wide information security program plan [frequency] and following [events] ; and

c. Protect the information security program plan from unauthorized disclosure and modification.
<<<
BASELINE: None
STATUS: Draft

[REQUIREMENT]
UID: PM-2
TITLE: PM-2 Information Security Program Leadership Role
STATEMENT: >>>
Appoint a senior agency information security officer with the mission and resources to coordinate, develop, implement, and maintain an organization-wide information security program.
<<<
BASELINE: None
STATUS: Draft

[REQUIREMENT]
UID: PM-3
TITLE: PM-3 Information Security and Privacy Resources
STATEMENT: >>>
a. Include the resources needed to implement the information security and privacy programs in capital planning and investment requests and document all exceptions to this requirement;

b. Prepare documentation required for addressing information security and privacy programs in capital planning and investment requests in accordance with applicable laws, executive orders, directives, policies, regulations, standards; and

c. Make available for expenditure, the planned information security and privacy resources.
<<<
COMMENT: Baselines: Privacy
BASELINE: Privacy
STATUS: Draft

[REQUIREMENT]
UID: PM-4
TITLE: PM-4 Plan of Action and Milestones Process
STATEMENT: >>>
a. Implement a process to ensure that plans of action and milestones for the information security, privacy, and supply chain risk management programs and associated organizational systems:

  1. Are developed and maintained;

  2. Document the remedial information security, privacy, and supply chain risk management actions to adequately respond to risk to organizational operations and assets, individuals, other organizations, and the Nation; and

  3. Are reported in accordance with established reporting requirements.

b. Review plans of action and milestones for consistency with the organizational risk management strategy and organization-wide priorities for risk response actions.
<<<
COMMENT: Baselines: Privacy
BASELINE: Privacy
STATUS: Draft

[REQUIREMENT]
UID: PM-5
TITLE: PM-5 System Inventory
STATEMENT: >>>
Develop and update [frequency] an inventory of organizational systems.
<<<
BASELINE: None
STATUS: Draft

[REQUIREMENT]
UID: PM-5.1
TITLE: PM-5(1) Inventory of Personally Identifiable Information
STATEMENT: >>>
Establish, maintain, and update [frequency] an inventory of all systems, applications, and projects that process personally identifiable information.
<<<
COMMENT: Baselines: Privacy
BASELINE: Privacy
STATUS: Draft

[REQUIREMENT]
UID: PM-6
TITLE: PM-6 Measures of Performance
STATEMENT: >>>
Develop, monitor, and report on the results of information security and privacy measures of performance.
<<<
COMMENT: Baselines: Privacy
BASELINE: Privacy
STATUS: Draft

[REQUIREMENT]
UID: PM-7
TITLE: PM-7 Enterprise Architecture
STATEMENT: >>>
Develop and maintain an enterprise architecture with consideration for information security, privacy, and the resulting risk to organizational operations and assets, individuals, other organizations, and the Nation.
<<<
COMMENT: Baselines: Privacy
BASELINE: Privacy
STATUS: Draft

[REQUIREMENT]
UID: PM-7.1
TITLE: PM-7(1) Offloading
STATEMENT: >>>
Offload [non-essential functions or services] to other systems, system components, or an external provider.
<<<
BASELINE: None
STATUS: Draft

[REQUIREMENT]
UID: PM-8
TITLE: PM-8 Critical Infrastructure Plan
STATEMENT: >>>
Address information security and privacy issues in the development, documentation, and updating of a critical infrastructure and key resources protection plan.
<<<
COMMENT: Baselines: Privacy
BASELINE: Privacy
STATUS: Draft

[REQUIREMENT]
UID: PM-9
TITLE: PM-9 Risk Management Strategy
STATEMENT: >>>
a. Develops a comprehensive strategy to manage:

  1. Security risk to organizational operations and assets, individuals, other organizations, and the Nation associated with the operation and use of organizational systems; and

  2. Privacy risk to individuals resulting from the authorized processing of personally identifiable information;

b. Implement the risk management strategy consistently across the organization; and

c. Review and update the risk management strategy [frequency] or as required, to address organizational changes.
<<<
COMMENT: Baselines: Privacy
BASELINE: Privacy
STATUS: Draft

[REQUIREMENT]
UID: PM-10
TITLE: PM-10 Authorization Process
STATEMENT: >>>
a. Manage the security and privacy state of organizational systems and the environments in which those systems operate through authorization processes;

b. Designate individuals to fulfill specific roles and responsibilities within the organizational risk management process; and

c. Integrate the authorization processes into an organization-wide risk management program.
<<<
COMMENT: Baselines: Privacy
BASELINE: Privacy
STATUS: Draft

[REQUIREMENT]
UID: PM-11
TITLE: PM-11 Mission and Business Process Definition
STATEMENT: >>>
a. Define organizational mission and business processes with consideration for information security and privacy and the resulting risk to organizational operations, organizational assets, individuals, other organizations, and the Nation; and

b. Determine information protection and personally identifiable information processing needs arising from the defined mission and business processes; and

c. Review and revise the mission and business processes [frequency].
<<<
COMMENT: Baselines: Privacy
BASELINE: Privacy
STATUS: Draft

[REQUIREMENT]
UID: PM-12
TITLE: PM-12 Insider Threat Program
STATEMENT: >>>
Implement an insider threat program that includes a cross-discipline insider threat incident handling team.
<<<
BASELINE: None
STATUS: Draft

[REQUIREMENT]
UID: PM-13
TITLE: PM-13 Security and Privacy Workforce
STATEMENT: >>>
Establish a security and privacy workforce development and improvement program.
<<<
COMMENT: Baselines: Privacy
BASELINE: Privacy
STATUS: Draft

[REQUIREMENT]
UID: PM-14
TITLE: PM-14 Testing, Training, and Monitoring
STATEMENT: >>>
a. Implement a process for ensuring that organizational plans for conducting security and privacy testing, training, and monitoring activities associated with organizational systems:

  1. Are developed and maintained; and

  2. Continue to be executed; and

b. Review testing, training, and monitoring plans for consistency with the organizational risk management strategy and organization-wide priorities for risk response actions.
<<<
COMMENT: Baselines: Privacy
BASELINE: Privacy
STATUS: Draft

[REQUIREMENT]
UID: PM-15
TITLE: PM-15 Security and Privacy Groups and Associations
STATEMENT: >>>
Establish and institutionalize contact with selected groups and associations within the security and privacy communities:

  a. To facilitate ongoing security and privacy education and training for organizational personnel;

  b. To maintain currency with recommended security and privacy practices, techniques, and technologies; and

  c. To share current security and privacy information, including threats, vulnerabilities, and incidents.
<<<
BASELINE: None
STATUS: Draft

[REQUIREMENT]
UID: PM-16
TITLE: PM-16 Threat Awareness Program
STATEMENT: >>>
Implement a threat awareness program that includes a cross-organization information-sharing capability for threat intelligence.
<<<
BASELINE: None
STATUS: Draft

[REQUIREMENT]
UID: PM-16.1
TITLE: PM-16(1) Automated Means for Sharing Threat Intelligence
STATEMENT: >>>
Employ automated mechanisms to maximize the effectiveness of sharing threat intelligence information.
<<<
BASELINE: None
STATUS: Draft

[REQUIREMENT]
UID: PM-17
TITLE: PM-17 Protecting Controlled Unclassified Information on External Systems
STATEMENT: >>>
a. Establish policy and procedures to ensure that requirements for the protection of controlled unclassified information that is processed, stored or transmitted on external systems, are implemented in accordance with applicable laws, executive orders, directives, policies, regulations, and standards; and

b. Review and update the policy and procedures [organization-defined frequency].
<<<
COMMENT: Baselines: Privacy
BASELINE: Privacy
STATUS: Draft

[REQUIREMENT]
UID: PM-18
TITLE: PM-18 Privacy Program Plan
STATEMENT: >>>
a. Develop and disseminate an organization-wide privacy program plan that provides an overview of the agency’s privacy program, and:

  1. Includes a description of the structure of the privacy program and the resources dedicated to the privacy program;

  2. Provides an overview of the requirements for the privacy program and a description of the privacy program management controls and common controls in place or planned for meeting those requirements;

  3. Includes the role of the senior agency official for privacy and the identification and assignment of roles of other privacy officials and staff and their responsibilities;

  4. Describes management commitment, compliance, and the strategic goals and objectives of the privacy program;

  5. Reflects coordination among organizational entities responsible for the different aspects of privacy; and

  6. Is approved by a senior official with responsibility and accountability for the privacy risk being incurred to organizational operations (including mission, functions, image, and reputation), organizational assets, individuals, other organizations, and the Nation; and

b. Update the plan [frequency] and to address changes in federal privacy laws and policy and organizational changes and problems identified during plan implementation or privacy control assessments.
<<<
COMMENT: Baselines: Privacy
BASELINE: Privacy
STATUS: Draft

[REQUIREMENT]
UID: PM-19
TITLE: PM-19 Privacy Program Leadership Role
STATEMENT: >>>
Appoint a senior agency official for privacy with the authority, mission, accountability, and resources to coordinate, develop, and implement, applicable privacy requirements and manage privacy risks through the organization-wide privacy program.
<<<
COMMENT: Baselines: Privacy
BASELINE: Privacy
STATUS: Draft

[REQUIREMENT]
UID: PM-20
TITLE: PM-20 Dissemination of Privacy Program Information
STATEMENT: >>>
Maintain a central resource webpage on the organization’s principal public website that serves as a central source of information about the organization’s privacy program and that:

  a. Ensures that the public has access to information about organizational privacy activities and can communicate with its senior agency official for privacy;

  b. Ensures that organizational privacy practices and reports are publicly available; and

  c. Employs publicly facing email addresses and/or phone lines to enable the public to provide feedback and/or direct questions to privacy offices regarding privacy practices.
<<<
COMMENT: Baselines: Privacy
BASELINE: Privacy
STATUS: Draft

[REQUIREMENT]
UID: PM-20.1
TITLE: PM-20(1) Privacy Policies on Websites, Applications, and Digital Services
STATEMENT: >>>
Develop and post privacy policies on all external-facing websites, mobile applications, and other digital services, that:

  (a) Are written in plain language and organized in a way that is easy to understand and navigate;

  (b) Provide information needed by the public to make an informed decision about whether and how to interact with the organization; and

  (c) Are updated whenever the organization makes a substantive change to the practices it describes and includes a time/date stamp to inform the public of the date of the most recent changes.
<<<
COMMENT: Baselines: Privacy
BASELINE: Privacy
STATUS: Draft

[REQUIREMENT]
UID: PM-21
TITLE: PM-21 Accounting of Disclosures
STATEMENT: >>>
a. Develop and maintain an accurate accounting of disclosures of personally identifiable information, including:

  1. Date, nature, and purpose of each disclosure; and

  2. Name and address, or other contact information of the individual or organization to which the disclosure was made;

b. Retain the accounting of disclosures for the length of the time the personally identifiable information is maintained or five years after the disclosure is made, whichever is longer; and

c. Make the accounting of disclosures available to the individual to whom the personally identifiable information relates upon request.
<<<
COMMENT: Baselines: Privacy
BASELINE: Privacy
STATUS: Draft

[REQUIREMENT]
UID: PM-22
TITLE: PM-22 Personally Identifiable Information Quality Management
STATEMENT: >>>
Develop and document organization-wide policies and procedures for:

  a. Reviewing for the accuracy, relevance, timeliness, and completeness of personally identifiable information across the information life cycle;

  b. Correcting or deleting inaccurate or outdated personally identifiable information;

  c. Disseminating notice of corrected or deleted personally identifiable information to individuals or other appropriate entities; and

  d. Appeals of adverse decisions on correction or deletion requests.
<<<
COMMENT: Baselines: Privacy
BASELINE: Privacy
STATUS: Draft

[REQUIREMENT]
UID: PM-23
TITLE: PM-23 Data Governance Body
STATEMENT: >>>
Establish a Data Governance Body consisting of [roles] with [responsibilities].
<<<
BASELINE: None
STATUS: Draft

[REQUIREMENT]
UID: PM-24
TITLE: PM-24 Data Integrity Board
STATEMENT: >>>
Establish a Data Integrity Board to:

  a. Review proposals to conduct or participate in a matching program; and

  b. Conduct an annual review of all matching programs in which the agency has participated.
<<<
COMMENT: Baselines: Privacy
BASELINE: Privacy
STATUS: Draft

[REQUIREMENT]
UID: PM-25
TITLE: PM-25 Minimization of Personally Identifiable Information Used in Testing, Training, and Research
STATEMENT: >>>
a. Develop, document, and implement policies and procedures that address the use of personally identifiable information for internal testing, training, and research;

b. Limit or minimize the amount of personally identifiable information used for internal testing, training, and research purposes;

c. Authorize the use of personally identifiable information when such information is required for internal testing, training, and research; and

d. Review and update policies and procedures [organization-defined frequency].
<<<
COMMENT: Baselines: Privacy
BASELINE: Privacy
STATUS: Draft

[REQUIREMENT]
UID: PM-26
TITLE: PM-26 Complaint Management
STATEMENT: >>>
Implement a process for receiving and responding to complaints, concerns, or questions from individuals about the organizational security and privacy practices that includes:

  a. Mechanisms that are easy to use and readily accessible by the public;

  b. All information necessary for successfully filing complaints;

  c. Tracking mechanisms to ensure all complaints received are reviewed and addressed within [organization-defined time period];

  d. Acknowledgement of receipt of complaints, concerns, or questions from individuals within [time period] ; and

  e. Response to complaints, concerns, or questions from individuals within [time period].
<<<
COMMENT: Baselines: Privacy
BASELINE: Privacy
STATUS: Draft

[REQUIREMENT]
UID: PM-27
TITLE: PM-27 Privacy Reporting
STATEMENT: >>>
a. Develop [privacy reports] and disseminate to:

  1. [oversight bodies] to demonstrate accountability with statutory, regulatory, and policy privacy mandates; and

  2. [officials] and other personnel with responsibility for monitoring privacy program compliance; and

b. Review and update privacy reports [frequency].
<<<
COMMENT: Baselines: Privacy
BASELINE: Privacy
STATUS: Draft

[REQUIREMENT]
UID: PM-28
TITLE: PM-28 Risk Framing
STATEMENT: >>>
a. Identify and document:

  1. Assumptions affecting risk assessments, risk responses, and risk monitoring;

  2. Constraints affecting risk assessments, risk responses, and risk monitoring;

  3. Priorities and trade-offs considered by the organization for managing risk; and

  4. Organizational risk tolerance;

b. Distribute the results of risk framing activities to [personnel] ; and

c. Review and update risk framing considerations [frequency].
<<<
COMMENT: Baselines: Privacy
BASELINE: Privacy
STATUS: Draft

[REQUIREMENT]
UID: PM-29
TITLE: PM-29 Risk Management Program Leadership Roles
STATEMENT: >>>
a. Appoint a Senior Accountable Official for Risk Management to align organizational information security and privacy management processes with strategic, operational, and budgetary planning processes; and

b. Establish a Risk Executive (function) to view and analyze risk from an organization-wide perspective and ensure management of risk is consistent across the organization.
<<<
BASELINE: None
STATUS: Draft

[REQUIREMENT]
UID: PM-30
TITLE: PM-30 Supply Chain Risk Management Strategy
STATEMENT: >>>
a. Develop an organization-wide strategy for managing supply chain risks associated with the development, acquisition, maintenance, and disposal of systems, system components, and system services;

b. Implement the supply chain risk management strategy consistently across the organization; and

c. Review and update the supply chain risk management strategy on [frequency] or as required, to address organizational changes.
<<<
BASELINE: None
STATUS: Draft

[REQUIREMENT]
UID: PM-30.1
TITLE: PM-30(1) Suppliers of Critical or Mission-essential Items
STATEMENT: >>>
Identify, prioritize, and assess suppliers of critical or mission-essential technologies, products, and services.
<<<
BASELINE: None
STATUS: Draft

[REQUIREMENT]
UID: PM-31
TITLE: PM-31 Continuous Monitoring Strategy
STATEMENT: >>>
Develop an organization-wide continuous monitoring strategy and implement continuous monitoring programs that include:

  a. Establishing the following organization-wide metrics to be monitored: [metrics];

  b. Establishing [monitoring frequencies] and [assessment frequencies] for control effectiveness;

  c. Ongoing monitoring of organizationally-defined metrics in accordance with the continuous monitoring strategy;

  d. Correlation and analysis of information generated by control assessments and monitoring;

  e. Response actions to address results of the analysis of control assessment and monitoring information; and

  f. Reporting the security and privacy status of organizational systems to [organization-defined personnel or roles] [organization-defined frequency].
<<<
COMMENT: Baselines: Privacy
BASELINE: Privacy
STATUS: Draft

[REQUIREMENT]
UID: PM-32
TITLE: PM-32 Purposing
STATEMENT: >>>
Analyze [systems or system components] supporting mission essential services or functions to ensure that the information resources are being used consistent with their intended purpose.
<<<
BASELINE: None
STATUS: Draft

[[/SECTION]]

[[SECTION]]
UID: NIST-PS
TITLE: PS — Personnel Security

[REQUIREMENT]
UID: PS-1
TITLE: PS-1 Policy and Procedures
STATEMENT: >>>
a. Develop, document, and disseminate to [organization-defined personnel or roles]:

  1. [ps-01_odp.03] personnel security policy that:

    (a) Addresses purpose, scope, roles, responsibilities, management commitment, coordination among organizational entities, and compliance; and

    (b) Is consistent with applicable laws, executive orders, directives, regulations, policies, standards, and guidelines; and

  2. Procedures to facilitate the implementation of the personnel security policy and the associated personnel security controls;

b. Designate an [official] to manage the development, documentation, and dissemination of the personnel security policy and procedures; and

c. Review and update the current personnel security:

  1. Policy [frequency] and following [events] ; and

  2. Procedures [frequency] and following [events].
<<<
COMMENT: Baselines: Low, Moderate, High
BASELINE: Low
STATUS: Draft

[REQUIREMENT]
UID: PS-2
TITLE: PS-2 Position Risk Designation
STATEMENT: >>>
a. Assign a risk designation to all organizational positions;

b. Establish screening criteria for individuals filling those positions; and

c. Review and update position risk designations [frequency].
<<<
COMMENT: Baselines: Low, Moderate, High
BASELINE: Low
STATUS: Draft

[REQUIREMENT]
UID: PS-3
TITLE: PS-3 Personnel Screening
STATEMENT: >>>
a. Screen individuals prior to authorizing access to the system; and

b. Rescreen individuals in accordance with [organization-defined conditions requiring rescreening and, where rescreening is so indicated, the frequency of rescreening].
<<<
COMMENT: Baselines: Low, Moderate, High
BASELINE: Low
STATUS: Draft

[REQUIREMENT]
UID: PS-3.1
TITLE: PS-3(1) Classified Information
STATEMENT: >>>
Verify that individuals accessing a system processing, storing, or transmitting classified information are cleared and indoctrinated to the highest classification level of the information to which they have access on the system.
<<<
BASELINE: None
STATUS: Draft

[REQUIREMENT]
UID: PS-3.2
TITLE: PS-3(2) Formal Indoctrination
STATEMENT: >>>
Verify that individuals accessing a system processing, storing, or transmitting types of classified information that require formal indoctrination, are formally indoctrinated for all the relevant types of information to which they have access on the system.
<<<
BASELINE: None
STATUS: Draft

[REQUIREMENT]
UID: PS-3.3
TITLE: PS-3(3) Information Requiring Special Protective Measures
STATEMENT: >>>
Verify that individuals accessing a system processing, storing, or transmitting information requiring special protection:

  (a) Have valid access authorizations that are demonstrated by assigned official government duties; and

  (b) Satisfy [additional personnel screening criteria].
<<<
BASELINE: None
STATUS: Draft

[REQUIREMENT]
UID: PS-3.4
TITLE: PS-3(4) Citizenship Requirements
STATEMENT: >>>
Verify that individuals accessing a system processing, storing, or transmitting [information types] meet [citizenship requirements].
<<<
BASELINE: None
STATUS: Draft

[REQUIREMENT]
UID: PS-4
TITLE: PS-4 Personnel Termination
STATEMENT: >>>
Upon termination of individual employment:

  a. Disable system access within [time period];

  b. Terminate or revoke any authenticators and credentials associated with the individual;

  c. Conduct exit interviews that include a discussion of [information security topics];

  d. Retrieve all security-related organizational system-related property; and

  e. Retain access to organizational information and systems formerly controlled by terminated individual.
<<<
COMMENT: Baselines: Low, Moderate, High
BASELINE: Low
STATUS: Draft

[REQUIREMENT]
UID: PS-4.1
TITLE: PS-4(1) Post-employment Requirements
STATEMENT: >>>
(a) Notify terminated individuals of applicable, legally binding post-employment requirements for the protection of organizational information; and

(b) Require terminated individuals to sign an acknowledgment of post-employment requirements as part of the organizational termination process.
<<<
BASELINE: None
STATUS: Draft

[REQUIREMENT]
UID: PS-4.2
TITLE: PS-4(2) Automated Actions
STATEMENT: >>>
Use [automated mechanisms] to [ps-04.02_odp.02].
<<<
COMMENT: Baselines: High
BASELINE: High
STATUS: Draft

[REQUIREMENT]
UID: PS-5
TITLE: PS-5 Personnel Transfer
STATEMENT: >>>
a. Review and confirm ongoing operational need for current logical and physical access authorizations to systems and facilities when individuals are reassigned or transferred to other positions within the organization;

b. Initiate [transfer or reassignment actions] within [time period following the formal transfer action];

c. Modify access authorization as needed to correspond with any changes in operational need due to reassignment or transfer; and

d. Notify [personnel or roles] within [time period].
<<<
COMMENT: Baselines: Low, Moderate, High
BASELINE: Low
STATUS: Draft

[REQUIREMENT]
UID: PS-6
TITLE: PS-6 Access Agreements
STATEMENT: >>>
a. Develop and document access agreements for organizational systems;

b. Review and update the access agreements [frequency] ; and

c. Verify that individuals requiring access to organizational information and systems:

  1. Sign appropriate access agreements prior to being granted access; and

  2. Re-sign access agreements to maintain access to organizational systems when access agreements have been updated or [frequency].
<<<
COMMENT: Baselines: Low, Moderate, High, Privacy
BASELINE: Low
STATUS: Draft

[REQUIREMENT]
UID: PS-6.1
TITLE: PS-6(1) Information Requiring Special Protection
STATEMENT: >>>
Withdrawn. Incorporated into PS-3.
<<<
COMMENT: Withdrawn
BASELINE: None
STATUS: Draft

[REQUIREMENT]
UID: PS-6.2
TITLE: PS-6(2) Classified Information Requiring Special Protection
STATEMENT: >>>
Verify that access to classified information requiring special protection is granted only to individuals who:

  (a) Have a valid access authorization that is demonstrated by assigned official government duties;

  (b) Satisfy associated personnel security criteria; and

  (c) Have read, understood, and signed a nondisclosure agreement.
<<<
BASELINE: None
STATUS: Draft

[REQUIREMENT]
UID: PS-6.3
TITLE: PS-6(3) Post-employment Requirements
STATEMENT: >>>
(a) Notify individuals of applicable, legally binding post-employment requirements for protection of organizational information; and

(b) Require individuals to sign an acknowledgment of these requirements, if applicable, as part of granting initial access to covered information.
<<<
BASELINE: None
STATUS: Draft

[REQUIREMENT]
UID: PS-7
TITLE: PS-7 External Personnel Security
STATEMENT: >>>
a. Establish personnel security requirements, including security roles and responsibilities for external providers;

b. Require external providers to comply with personnel security policies and procedures established by the organization;

c. Document personnel security requirements;

d. Require external providers to notify [personnel or roles] of any personnel transfers or terminations of external personnel who possess organizational credentials and/or badges, or who have system privileges within [time period] ; and

e. Monitor provider compliance with personnel security requirements.
<<<
COMMENT: Baselines: Low, Moderate, High
BASELINE: Low
STATUS: Draft

[REQUIREMENT]
UID: PS-8
TITLE: PS-8 Personnel Sanctions
STATEMENT: >>>
a. Employ a formal sanctions process for individuals failing to comply with established information security and privacy policies and procedures; and

b. Notify [personnel or roles] within [time period] when a formal employee sanctions process is initiated, identifying the individual sanctioned and the reason for the sanction.
<<<
COMMENT: Baselines: Low, Moderate, High
BASELINE: Low
STATUS: Draft

[REQUIREMENT]
UID: PS-9
TITLE: PS-9 Position Descriptions
STATEMENT: >>>
Incorporate security and privacy roles and responsibilities into organizational position descriptions.
<<<
COMMENT: Baselines: Low, Moderate, High
BASELINE: Low
STATUS: Draft

[[/SECTION]]

[[SECTION]]
UID: NIST-PT
TITLE: PT — Personally Identifiable Information Processing and Transparency

[REQUIREMENT]
UID: PT-1
TITLE: PT-1 Policy and Procedures
STATEMENT: >>>
a. Develop, document, and disseminate to [organization-defined personnel or roles]:

  1. [pt-01_odp.03] personally identifiable information processing and transparency policy that:

    (a) Addresses purpose, scope, roles, responsibilities, management commitment, coordination among organizational entities, and compliance; and

    (b) Is consistent with applicable laws, executive orders, directives, regulations, policies, standards, and guidelines; and

  2. Procedures to facilitate the implementation of the personally identifiable information processing and transparency policy and the associated personally identifiable information processing and transparency controls;

b. Designate an [official] to manage the development, documentation, and dissemination of the personally identifiable information processing and transparency policy and procedures; and

c. Review and update the current personally identifiable information processing and transparency:

  1. Policy [frequency] and following [events] ; and

  2. Procedures [frequency] and following [events].
<<<
COMMENT: Baselines: Privacy
BASELINE: Privacy
STATUS: Draft

[REQUIREMENT]
UID: PT-2
TITLE: PT-2 Authority to Process Personally Identifiable Information
STATEMENT: >>>
a. Determine and document the [authority] that permits the [processing] of personally identifiable information; and

b. Restrict the [processing] of personally identifiable information to only that which is authorized.
<<<
COMMENT: Baselines: Privacy
BASELINE: Privacy
STATUS: Draft

[REQUIREMENT]
UID: PT-2.1
TITLE: PT-2(1) Data Tagging
STATEMENT: >>>
Attach data tags containing [authorized processing] to [elements of personally identifiable information].
<<<
BASELINE: None
STATUS: Draft

[REQUIREMENT]
UID: PT-2.2
TITLE: PT-2(2) Automation
STATEMENT: >>>
Manage enforcement of the authorized processing of personally identifiable information using [automated mechanisms].
<<<
BASELINE: None
STATUS: Draft

[REQUIREMENT]
UID: PT-3
TITLE: PT-3 Personally Identifiable Information Processing Purposes
STATEMENT: >>>
a. Identify and document the [purpose(s)] for processing personally identifiable information;

b. Describe the purpose(s) in the public privacy notices and policies of the organization;

c. Restrict the [processing] of personally identifiable information to only that which is compatible with the identified purpose(s); and

d. Monitor changes in processing personally identifiable information and implement [mechanisms] to ensure that any changes are made in accordance with [requirements].
<<<
COMMENT: Baselines: Privacy
BASELINE: Privacy
STATUS: Draft

[REQUIREMENT]
UID: PT-3.1
TITLE: PT-3(1) Data Tagging
STATEMENT: >>>
Attach data tags containing the following purposes to [elements of personally identifiable information]: [processing purposes].
<<<
BASELINE: None
STATUS: Draft

[REQUIREMENT]
UID: PT-3.2
TITLE: PT-3(2) Automation
STATEMENT: >>>
Track processing purposes of personally identifiable information using [automated mechanisms].
<<<
BASELINE: None
STATUS: Draft

[REQUIREMENT]
UID: PT-4
TITLE: PT-4 Consent
STATEMENT: >>>
Implement [tools or mechanisms] for individuals to consent to the processing of their personally identifiable information prior to its collection that facilitate individuals’ informed decision-making.
<<<
COMMENT: Baselines: Privacy
BASELINE: Privacy
STATUS: Draft

[REQUIREMENT]
UID: PT-4.1
TITLE: PT-4(1) Tailored Consent
STATEMENT: >>>
Provide [mechanisms] to allow individuals to tailor processing permissions to selected elements of personally identifiable information.
<<<
BASELINE: None
STATUS: Draft

[REQUIREMENT]
UID: PT-4.2
TITLE: PT-4(2) Just-in-time Consent
STATEMENT: >>>
Present [consent mechanisms] to individuals at [frequency] and in conjunction with [personally identifiable information processing].
<<<
BASELINE: None
STATUS: Draft

[REQUIREMENT]
UID: PT-4.3
TITLE: PT-4(3) Revocation
STATEMENT: >>>
Implement [tools or mechanisms] for individuals to revoke consent to the processing of their personally identifiable information.
<<<
BASELINE: None
STATUS: Draft

[REQUIREMENT]
UID: PT-5
TITLE: PT-5 Privacy Notice
STATEMENT: >>>
Provide notice to individuals about the processing of personally identifiable information that:

  a. Is available to individuals upon first interacting with an organization, and subsequently at [frequency];

  b. Is clear and easy-to-understand, expressing information about personally identifiable information processing in plain language;

  c. Identifies the authority that authorizes the processing of personally identifiable information;

  d. Identifies the purposes for which personally identifiable information is to be processed; and

  e. Includes [information].
<<<
COMMENT: Baselines: Privacy
BASELINE: Privacy
STATUS: Draft

[REQUIREMENT]
UID: PT-5.1
TITLE: PT-5(1) Just-in-time Notice
STATEMENT: >>>
Present notice of personally identifiable information processing to individuals at a time and location where the individual provides personally identifiable information or in conjunction with a data action, or [frequency].
<<<
BASELINE: None
STATUS: Draft

[REQUIREMENT]
UID: PT-5.2
TITLE: PT-5(2) Privacy Act Statements
STATEMENT: >>>
Include Privacy Act statements on forms that collect information that will be maintained in a Privacy Act system of records, or provide Privacy Act statements on separate forms that can be retained by individuals.
<<<
COMMENT: Baselines: Privacy
BASELINE: Privacy
STATUS: Draft

[REQUIREMENT]
UID: PT-6
TITLE: PT-6 System of Records Notice
STATEMENT: >>>
For systems that process information that will be maintained in a Privacy Act system of records:

  a. Draft system of records notices in accordance with OMB guidance and submit new and significantly modified system of records notices to the OMB and appropriate congressional committees for advance review;

  b. Publish system of records notices in the Federal Register; and

  c. Keep system of records notices accurate, up-to-date, and scoped in accordance with policy.
<<<
COMMENT: Baselines: Privacy
BASELINE: Privacy
STATUS: Draft

[REQUIREMENT]
UID: PT-6.1
TITLE: PT-6(1) Routine Uses
STATEMENT: >>>
Review all routine uses published in the system of records notice at [frequency] to ensure continued accuracy, and to ensure that routine uses continue to be compatible with the purpose for which the information was collected.
<<<
COMMENT: Baselines: Privacy
BASELINE: Privacy
STATUS: Draft

[REQUIREMENT]
UID: PT-6.2
TITLE: PT-6(2) Exemption Rules
STATEMENT: >>>
Review all Privacy Act exemptions claimed for the system of records at [frequency] to ensure they remain appropriate and necessary in accordance with law, that they have been promulgated as regulations, and that they are accurately described in the system of records notice.
<<<
COMMENT: Baselines: Privacy
BASELINE: Privacy
STATUS: Draft

[REQUIREMENT]
UID: PT-7
TITLE: PT-7 Specific Categories of Personally Identifiable Information
STATEMENT: >>>
Apply [processing conditions] for specific categories of personally identifiable information.
<<<
COMMENT: Baselines: Privacy
BASELINE: Privacy
STATUS: Draft

[REQUIREMENT]
UID: PT-7.1
TITLE: PT-7(1) Social Security Numbers
STATEMENT: >>>
When a system processes Social Security numbers:

  (a) Eliminate unnecessary collection, maintenance, and use of Social Security numbers, and explore alternatives to their use as a personal identifier;

  (b) Do not deny any individual any right, benefit, or privilege provided by law because of such individual’s refusal to disclose his or her Social Security number; and

  (c) Inform any individual who is asked to disclose his or her Social Security number whether that disclosure is mandatory or voluntary, by what statutory or other authority such number is solicited, and what uses will be made of it.
<<<
COMMENT: Baselines: Privacy
BASELINE: Privacy
STATUS: Draft

[REQUIREMENT]
UID: PT-7.2
TITLE: PT-7(2) First Amendment Information
STATEMENT: >>>
Prohibit the processing of information describing how any individual exercises rights guaranteed by the First Amendment unless expressly authorized by statute or by the individual or unless pertinent to and within the scope of an authorized law enforcement activity.
<<<
COMMENT: Baselines: Privacy
BASELINE: Privacy
STATUS: Draft

[REQUIREMENT]
UID: PT-8
TITLE: PT-8 Computer Matching Requirements
STATEMENT: >>>
When a system or organization processes information for the purpose of conducting a matching program:

  a. Obtain approval from the Data Integrity Board to conduct the matching program;

  b. Develop and enter into a computer matching agreement;

  c. Publish a matching notice in the Federal Register;

  d. Independently verify the information produced by the matching program before taking adverse action against an individual, if required; and

  e. Provide individuals with notice and an opportunity to contest the findings before taking adverse action against an individual.
<<<
COMMENT: Baselines: Privacy
BASELINE: Privacy
STATUS: Draft

[[/SECTION]]

[[SECTION]]
UID: NIST-RA
TITLE: RA — Risk Assessment

[REQUIREMENT]
UID: RA-1
TITLE: RA-1 Policy and Procedures
STATEMENT: >>>
a. Develop, document, and disseminate to [organization-defined personnel or roles]:

  1. [ra-01_odp.03] risk assessment policy that:

    (a) Addresses purpose, scope, roles, responsibilities, management commitment, coordination among organizational entities, and compliance; and

    (b) Is consistent with applicable laws, executive orders, directives, regulations, policies, standards, and guidelines; and

  2. Procedures to facilitate the implementation of the risk assessment policy and the associated risk assessment controls;

b. Designate an [official] to manage the development, documentation, and dissemination of the risk assessment policy and procedures; and

c. Review and update the current risk assessment:

  1. Policy [frequency] and following [events] ; and

  2. Procedures [frequency] and following [events].
<<<
COMMENT: Baselines: Low, Moderate, High, Privacy
BASELINE: Low
STATUS: Draft

[REQUIREMENT]
UID: RA-2
TITLE: RA-2 Security Categorization
STATEMENT: >>>
a. Categorize the system and information it processes, stores, and transmits;

b. Document the security categorization results, including supporting rationale, in the security plan for the system; and

c. Verify that the authorizing official or authorizing official designated representative reviews and approves the security categorization decision.
<<<
COMMENT: Baselines: Low, Moderate, High
BASELINE: Low
STATUS: Draft

[REQUIREMENT]
UID: RA-2.1
TITLE: RA-2(1) Impact-level Prioritization
STATEMENT: >>>
Conduct an impact-level prioritization of organizational systems to obtain additional granularity on system impact levels.
<<<
BASELINE: None
STATUS: Draft

[REQUIREMENT]
UID: RA-3
TITLE: RA-3 Risk Assessment
STATEMENT: >>>
a. Conduct a risk assessment, including:

  1. Identifying threats to and vulnerabilities in the system;

  2. Determining the likelihood and magnitude of harm from unauthorized access, use, disclosure, disruption, modification, or destruction of the system, the information it processes, stores, or transmits, and any related information; and

  3. Determining the likelihood and impact of adverse effects on individuals arising from the processing of personally identifiable information;

b. Integrate risk assessment results and risk management decisions from the organization and mission or business process perspectives with system-level risk assessments;

c. Document risk assessment results in [ra-03_odp.01];

d. Review risk assessment results [frequency];

e. Disseminate risk assessment results to [personnel or roles] ; and

f. Update the risk assessment [frequency] or when there are significant changes to the system, its environment of operation, or other conditions that may impact the security or privacy state of the system.
<<<
COMMENT: Baselines: Low, Moderate, High, Privacy
BASELINE: Low
STATUS: Draft

[REQUIREMENT]
UID: RA-3.1
TITLE: RA-3(1) Supply Chain Risk Assessment
STATEMENT: >>>
(a) Assess supply chain risks associated with [systems, system components, and system services] ; and

(b) Update the supply chain risk assessment [frequency] , when there are significant changes to the relevant supply chain, or when changes to the system, environments of operation, or other conditions may necessitate a change in the supply chain.
<<<
COMMENT: Baselines: Low, Moderate, High
BASELINE: Low
STATUS: Draft

[REQUIREMENT]
UID: RA-3.2
TITLE: RA-3(2) Use of All-source Intelligence
STATEMENT: >>>
Use all-source intelligence to assist in the analysis of risk.
<<<
BASELINE: None
STATUS: Draft

[REQUIREMENT]
UID: RA-3.3
TITLE: RA-3(3) Dynamic Threat Awareness
STATEMENT: >>>
Determine the current cyber threat environment on an ongoing basis using [means].
<<<
BASELINE: None
STATUS: Draft

[REQUIREMENT]
UID: RA-3.4
TITLE: RA-3(4) Predictive Cyber Analytics
STATEMENT: >>>
Employ the following advanced automation and analytics capabilities to predict and identify risks to [systems or system components]: [organization-defined advanced automation and analytics capabilities].
<<<
BASELINE: None
STATUS: Draft

[REQUIREMENT]
UID: RA-4
TITLE: RA-4 Risk Assessment Update
STATEMENT: >>>
Withdrawn. Incorporated into RA-3.
<<<
COMMENT: Withdrawn
BASELINE: None
STATUS: Draft

[REQUIREMENT]
UID: RA-5
TITLE: RA-5 Vulnerability Monitoring and Scanning
STATEMENT: >>>
a. Monitor and scan for vulnerabilities in the system and hosted applications [organization-defined frequency and/or randomly in accordance with organization-defined process] and when new vulnerabilities potentially affecting the system are identified and reported;

b. Employ vulnerability monitoring tools and techniques that facilitate interoperability among tools and automate parts of the vulnerability management process by using standards for:

  1. Enumerating platforms, software flaws, and improper configurations;

  2. Formatting checklists and test procedures; and

  3. Measuring vulnerability impact;

c. Analyze vulnerability scan reports and results from vulnerability monitoring;

d. Remediate legitimate vulnerabilities [response times] in accordance with an organizational assessment of risk;

e. Share information obtained from the vulnerability monitoring process and control assessments with [personnel or roles] to help eliminate similar vulnerabilities in other systems; and

f. Employ vulnerability monitoring tools that include the capability to readily update the vulnerabilities to be scanned.
<<<
COMMENT: Baselines: Low, Moderate, High
BASELINE: Low
STATUS: Draft

[REQUIREMENT]
UID: RA-5.1
TITLE: RA-5(1) Update Tool Capability
STATEMENT: >>>
Withdrawn. Incorporated into RA-5.
<<<
COMMENT: Withdrawn
BASELINE: None
STATUS: Draft

[REQUIREMENT]
UID: RA-5.2
TITLE: RA-5(2) Update Vulnerabilities to Be Scanned
STATEMENT: >>>
Update the system vulnerabilities to be scanned [ra-05.02_odp.01].
<<<
COMMENT: Baselines: Low, Moderate, High
BASELINE: Low
STATUS: Draft

[REQUIREMENT]
UID: RA-5.3
TITLE: RA-5(3) Breadth and Depth of Coverage
STATEMENT: >>>
Define the breadth and depth of vulnerability scanning coverage.
<<<
BASELINE: None
STATUS: Draft

[REQUIREMENT]
UID: RA-5.4
TITLE: RA-5(4) Discoverable Information
STATEMENT: >>>
Determine information about the system that is discoverable and take [corrective actions].
<<<
COMMENT: Baselines: High
BASELINE: High
STATUS: Draft

[REQUIREMENT]
UID: RA-5.5
TITLE: RA-5(5) Privileged Access
STATEMENT: >>>
Implement privileged access authorization to [system components] for [vulnerability scanning activities].
<<<
COMMENT: Baselines: Moderate, High
BASELINE: Moderate
STATUS: Draft

[REQUIREMENT]
UID: RA-5.6
TITLE: RA-5(6) Automated Trend Analyses
STATEMENT: >>>
Compare the results of multiple vulnerability scans using [automated mechanisms].
<<<
BASELINE: None
STATUS: Draft

[REQUIREMENT]
UID: RA-5.7
TITLE: RA-5(7) Automated Detection and Notification of Unauthorized Components
STATEMENT: >>>
Withdrawn. Incorporated into CM-8.
<<<
COMMENT: Withdrawn
BASELINE: None
STATUS: Draft

[REQUIREMENT]
UID: RA-5.8
TITLE: RA-5(8) Review Historic Audit Logs
STATEMENT: >>>
Review historic audit logs to determine if a vulnerability identified in a [system] has been previously exploited within an [time period].
<<<
BASELINE: None
STATUS: Draft

[REQUIREMENT]
UID: RA-5.9
TITLE: RA-5(9) Penetration Testing and Analyses
STATEMENT: >>>
Withdrawn. Incorporated into CA-8.
<<<
COMMENT: Withdrawn
BASELINE: None
STATUS: Draft

[REQUIREMENT]
UID: RA-5.10
TITLE: RA-5(10) Correlate Scanning Information
STATEMENT: >>>
Correlate the output from vulnerability scanning tools to determine the presence of multi-vulnerability and multi-hop attack vectors.
<<<
BASELINE: None
STATUS: Draft

[REQUIREMENT]
UID: RA-5.11
TITLE: RA-5(11) Public Disclosure Program
STATEMENT: >>>
Establish a public reporting channel for receiving reports of vulnerabilities in organizational systems and system components.
<<<
COMMENT: Baselines: Low, Moderate, High
BASELINE: Low
STATUS: Draft

[REQUIREMENT]
UID: RA-6
TITLE: RA-6 Technical Surveillance Countermeasures Survey
STATEMENT: >>>
Employ a technical surveillance countermeasures survey at [locations] [ra-06_odp.02].
<<<
BASELINE: None
STATUS: Draft

[REQUIREMENT]
UID: RA-7
TITLE: RA-7 Risk Response
STATEMENT: >>>
Respond to findings from security and privacy assessments, monitoring, and audits in accordance with organizational risk tolerance.
<<<
COMMENT: Baselines: Low, Moderate, High, Privacy
BASELINE: Low
STATUS: Draft

[REQUIREMENT]
UID: RA-8
TITLE: RA-8 Privacy Impact Assessments
STATEMENT: >>>
Conduct privacy impact assessments for systems, programs, or other activities before:

  a. Developing or procuring information technology that processes personally identifiable information; and

  b. Initiating a new collection of personally identifiable information that:

    1. Will be processed using information technology; and

    2. Includes personally identifiable information permitting the physical or virtual (online) contacting of a specific individual, if identical questions have been posed to, or identical reporting requirements imposed on, ten or more individuals, other than agencies, instrumentalities, or employees of the federal government.
<<<
COMMENT: Baselines: Privacy
BASELINE: Privacy
STATUS: Draft

[REQUIREMENT]
UID: RA-9
TITLE: RA-9 Criticality Analysis
STATEMENT: >>>
Identify critical system components and functions by performing a criticality analysis for [systems, system components, or system services] at [decision points in the system development life cycle].
<<<
COMMENT: Baselines: Moderate, High
BASELINE: Moderate
STATUS: Draft

[REQUIREMENT]
UID: RA-10
TITLE: RA-10 Threat Hunting
STATEMENT: >>>
a. Establish and maintain a cyber threat hunting capability to:

  1. Search for indicators of compromise in organizational systems; and

  2. Detect, track, and disrupt threats that evade existing controls; and

b. Employ the threat hunting capability [frequency].
<<<
BASELINE: None
STATUS: Draft

[[/SECTION]]

[[SECTION]]
UID: NIST-SA
TITLE: SA — System and Services Acquisition

[REQUIREMENT]
UID: SA-1
TITLE: SA-1 Policy and Procedures
STATEMENT: >>>
a. Develop, document, and disseminate to [organization-defined personnel or roles]:

  1. [sa-01_odp.03] system and services acquisition policy that:

    (a) Addresses purpose, scope, roles, responsibilities, management commitment, coordination among organizational entities, and compliance; and

    (b) Is consistent with applicable laws, executive orders, directives, regulations, policies, standards, and guidelines; and

  2. Procedures to facilitate the implementation of the system and services acquisition policy and the associated system and services acquisition controls;

b. Designate an [official] to manage the development, documentation, and dissemination of the system and services acquisition policy and procedures; and

c. Review and update the current system and services acquisition:

  1. Policy [frequency] and following [events] ; and

  2. Procedures [frequency] and following [events].
<<<
COMMENT: Baselines: Low, Moderate, High, Privacy
BASELINE: Low
STATUS: Draft

[REQUIREMENT]
UID: SA-2
TITLE: SA-2 Allocation of Resources
STATEMENT: >>>
a. Determine the high-level information security and privacy requirements for the system or system service in mission and business process planning;

b. Determine, document, and allocate the resources required to protect the system or system service as part of the organizational capital planning and investment control process; and

c. Establish a discrete line item for information security and privacy in organizational programming and budgeting documentation.
<<<
COMMENT: Baselines: Low, Moderate, High, Privacy
BASELINE: Low
STATUS: Draft

[REQUIREMENT]
UID: SA-3
TITLE: SA-3 System Development Life Cycle
STATEMENT: >>>
a. Acquire, develop, and manage the system using [system-development life cycle] that incorporates information security and privacy considerations;

b. Define and document information security and privacy roles and responsibilities throughout the system development life cycle;

c. Identify individuals having information security and privacy roles and responsibilities; and

d. Integrate the organizational information security and privacy risk management process into system development life cycle activities.
<<<
COMMENT: Baselines: Low, Moderate, High, Privacy
BASELINE: Low
STATUS: Draft

[REQUIREMENT]
UID: SA-3.1
TITLE: SA-3(1) Manage Preproduction Environment
STATEMENT: >>>
Protect system preproduction environments commensurate with risk throughout the system development life cycle for the system, system component, or system service.
<<<
BASELINE: None
STATUS: Draft

[REQUIREMENT]
UID: SA-3.2
TITLE: SA-3(2) Use of Live or Operational Data
STATEMENT: >>>
(a) Approve, document, and control the use of live data in preproduction environments for the system, system component, or system service; and

(b) Protect preproduction environments for the system, system component, or system service at the same impact or classification level as any live data in use within the preproduction environments.
<<<
BASELINE: None
STATUS: Draft

[REQUIREMENT]
UID: SA-3.3
TITLE: SA-3(3) Technology Refresh
STATEMENT: >>>
Plan for and implement a technology refresh schedule for the system throughout the system development life cycle.
<<<
BASELINE: None
STATUS: Draft

[REQUIREMENT]
UID: SA-4
TITLE: SA-4 Acquisition Process
STATEMENT: >>>
Include the following requirements, descriptions, and criteria, explicitly or by reference, using [sa-04_odp.01] in the acquisition contract for the system, system component, or system service:

  a. Security and privacy functional requirements;

  b. Strength of mechanism requirements;

  c. Security and privacy assurance requirements;

  d. Controls needed to satisfy the security and privacy requirements.

  e. Security and privacy documentation requirements;

  f. Requirements for protecting security and privacy documentation;

  g. Description of the system development environment and environment in which the system is intended to operate;

  h. Allocation of responsibility or identification of parties responsible for information security, privacy, and supply chain risk management; and

  i. Acceptance criteria.
<<<
COMMENT: Baselines: Low, Moderate, High, Privacy
BASELINE: Low
STATUS: Draft

[REQUIREMENT]
UID: SA-4.1
TITLE: SA-4(1) Functional Properties of Controls
STATEMENT: >>>
Require the developer of the system, system component, or system service to provide a description of the functional properties of the controls to be implemented.
<<<
COMMENT: Baselines: Moderate, High
BASELINE: Moderate
STATUS: Draft

[REQUIREMENT]
UID: SA-4.2
TITLE: SA-4(2) Design and Implementation Information for Controls
STATEMENT: >>>
Require the developer of the system, system component, or system service to provide design and implementation information for the controls that includes: [sa-04.02_odp.01] at [level of detail].
<<<
COMMENT: Baselines: Moderate, High
BASELINE: Moderate
STATUS: Draft

[REQUIREMENT]
UID: SA-4.3
TITLE: SA-4(3) Development Methods, Techniques, and Practices
STATEMENT: >>>
Require the developer of the system, system component, or system service to demonstrate the use of a system development life cycle process that includes:

  (a) [systems engineering methods];

  (b) [sa-04.03_odp.02] ; and

  (c) [sa-04.03_odp.05].
<<<
BASELINE: None
STATUS: Draft

[REQUIREMENT]
UID: SA-4.4
TITLE: SA-4(4) Assignment of Components to Systems
STATEMENT: >>>
Withdrawn. Incorporated into CM-8.9.
<<<
COMMENT: Withdrawn
BASELINE: None
STATUS: Draft

[REQUIREMENT]
UID: SA-4.5
TITLE: SA-4(5) System, Component, and Service Configurations
STATEMENT: >>>
Require the developer of the system, system component, or system service to:

  (a) Deliver the system, component, or service with [security configurations] implemented; and

  (b) Use the configurations as the default for any subsequent system, component, or service reinstallation or upgrade.
<<<
COMMENT: Baselines: High
BASELINE: High
STATUS: Draft

[REQUIREMENT]
UID: SA-4.6
TITLE: SA-4(6) Use of Information Assurance Products
STATEMENT: >>>
(a) Employ only government off-the-shelf or commercial off-the-shelf information assurance and information assurance-enabled information technology products that compose an NSA-approved solution to protect classified information when the networks used to transmit the information are at a lower classification level than the information being transmitted; and

(b) Ensure that these products have been evaluated and/or validated by NSA or in accordance with NSA-approved procedures.
<<<
BASELINE: None
STATUS: Draft

[REQUIREMENT]
UID: SA-4.7
TITLE: SA-4(7) NIAP-approved Protection Profiles
STATEMENT: >>>
(a) Limit the use of commercially provided information assurance and information assurance-enabled information technology products to those products that have been successfully evaluated against a National Information Assurance partnership (NIAP)-approved Protection Profile for a specific technology type, if such a profile exists; and

(b) Require, if no NIAP-approved Protection Profile exists for a specific technology type but a commercially provided information technology product relies on cryptographic functionality to enforce its security policy, that the cryptographic module is FIPS-validated or NSA-approved.
<<<
BASELINE: None
STATUS: Draft

[REQUIREMENT]
UID: SA-4.8
TITLE: SA-4(8) Continuous Monitoring Plan for Controls
STATEMENT: >>>
Require the developer of the system, system component, or system service to produce a plan for continuous monitoring of control effectiveness that is consistent with the continuous monitoring program of the organization.
<<<
BASELINE: None
STATUS: Draft

[REQUIREMENT]
UID: SA-4.9
TITLE: SA-4(9) Functions, Ports, Protocols, and Services in Use
STATEMENT: >>>
Require the developer of the system, system component, or system service to identify the functions, ports, protocols, and services intended for organizational use.
<<<
COMMENT: Baselines: Moderate, High
BASELINE: Moderate
STATUS: Draft

[REQUIREMENT]
UID: SA-4.10
TITLE: SA-4(10) Use of Approved PIV Products
STATEMENT: >>>
Employ only information technology products on the FIPS 201-approved products list for Personal Identity Verification (PIV) capability implemented within organizational systems.
<<<
COMMENT: Baselines: Low, Moderate, High
BASELINE: Low
STATUS: Draft

[REQUIREMENT]
UID: SA-4.11
TITLE: SA-4(11) System of Records
STATEMENT: >>>
Include [Privacy Act requirements] in the acquisition contract for the operation of a system of records on behalf of an organization to accomplish an organizational mission or function.
<<<
BASELINE: None
STATUS: Draft

[REQUIREMENT]
UID: SA-4.12
TITLE: SA-4(12) Data Ownership
STATEMENT: >>>
(a) Include organizational data ownership requirements in the acquisition contract; and

(b) Require all data to be removed from the contractor’s system and returned to the organization within [time frame].
<<<
BASELINE: None
STATUS: Draft

[REQUIREMENT]
UID: SA-5
TITLE: SA-5 System Documentation
STATEMENT: >>>
a. Obtain or develop administrator documentation for the system, system component, or system service that describes:

  1. Secure configuration, installation, and operation of the system, component, or service;

  2. Effective use and maintenance of security and privacy functions and mechanisms; and

  3. Known vulnerabilities regarding configuration and use of administrative or privileged functions;

b. Obtain or develop user documentation for the system, system component, or system service that describes:

  1. User-accessible security and privacy functions and mechanisms and how to effectively use those functions and mechanisms;

  2. Methods for user interaction, which enables individuals to use the system, component, or service in a more secure manner and protect individual privacy; and

  3. User responsibilities in maintaining the security of the system, component, or service and privacy of individuals;

c. Document attempts to obtain system, system component, or system service documentation when such documentation is either unavailable or nonexistent and take [actions] in response; and

d. Distribute documentation to [personnel or roles].
<<<
COMMENT: Baselines: Low, Moderate, High
BASELINE: Low
STATUS: Draft

[REQUIREMENT]
UID: SA-5.1
TITLE: SA-5(1) Functional Properties of Security Controls
STATEMENT: >>>
Withdrawn. Incorporated into SA-4.1.
<<<
COMMENT: Withdrawn
BASELINE: None
STATUS: Draft

[REQUIREMENT]
UID: SA-5.2
TITLE: SA-5(2) Security-relevant External System Interfaces
STATEMENT: >>>
Withdrawn. Incorporated into SA-4.2.
<<<
COMMENT: Withdrawn
BASELINE: None
STATUS: Draft

[REQUIREMENT]
UID: SA-5.3
TITLE: SA-5(3) High-level Design
STATEMENT: >>>
Withdrawn. Incorporated into SA-4.2.
<<<
COMMENT: Withdrawn
BASELINE: None
STATUS: Draft

[REQUIREMENT]
UID: SA-5.4
TITLE: SA-5(4) Low-level Design
STATEMENT: >>>
Withdrawn. Incorporated into SA-4.2.
<<<
COMMENT: Withdrawn
BASELINE: None
STATUS: Draft

[REQUIREMENT]
UID: SA-5.5
TITLE: SA-5(5) Source Code
STATEMENT: >>>
Withdrawn. Incorporated into SA-4.2.
<<<
COMMENT: Withdrawn
BASELINE: None
STATUS: Draft

[REQUIREMENT]
UID: SA-6
TITLE: SA-6 Software Usage Restrictions
STATEMENT: >>>
Withdrawn. Incorporated into CM-10, SI-7.
<<<
COMMENT: Withdrawn
BASELINE: None
STATUS: Draft

[REQUIREMENT]
UID: SA-7
TITLE: SA-7 User-installed Software
STATEMENT: >>>
Withdrawn. Incorporated into CM-11, SI-7.
<<<
COMMENT: Withdrawn
BASELINE: None
STATUS: Draft

[REQUIREMENT]
UID: SA-8
TITLE: SA-8 Security and Privacy Engineering Principles
STATEMENT: >>>
Apply the following systems security and privacy engineering principles in the specification, design, development, implementation, and modification of the system and system components: [organization-defined systems security and privacy engineering principles].
<<<
COMMENT: Baselines: Low, Moderate, High
BASELINE: Low
STATUS: Draft

[REQUIREMENT]
UID: SA-8.1
TITLE: SA-8(1) Clear Abstractions
STATEMENT: >>>
Implement the security design principle of clear abstractions.
<<<
BASELINE: None
STATUS: Draft

[REQUIREMENT]
UID: SA-8.2
TITLE: SA-8(2) Least Common Mechanism
STATEMENT: >>>
Implement the security design principle of least common mechanism in [systems or system components].
<<<
BASELINE: None
STATUS: Draft

[REQUIREMENT]
UID: SA-8.3
TITLE: SA-8(3) Modularity and Layering
STATEMENT: >>>
Implement the security design principles of modularity and layering in [organization-defined systems or system components].
<<<
BASELINE: None
STATUS: Draft

[REQUIREMENT]
UID: SA-8.4
TITLE: SA-8(4) Partially Ordered Dependencies
STATEMENT: >>>
Implement the security design principle of partially ordered dependencies in [systems or system components].
<<<
BASELINE: None
STATUS: Draft

[REQUIREMENT]
UID: SA-8.5
TITLE: SA-8(5) Efficiently Mediated Access
STATEMENT: >>>
Implement the security design principle of efficiently mediated access in [systems or system components].
<<<
BASELINE: None
STATUS: Draft

[REQUIREMENT]
UID: SA-8.6
TITLE: SA-8(6) Minimized Sharing
STATEMENT: >>>
Implement the security design principle of minimized sharing in [systems or system components].
<<<
BASELINE: None
STATUS: Draft

[REQUIREMENT]
UID: SA-8.7
TITLE: SA-8(7) Reduced Complexity
STATEMENT: >>>
Implement the security design principle of reduced complexity in [systems or system components].
<<<
BASELINE: None
STATUS: Draft

[REQUIREMENT]
UID: SA-8.8
TITLE: SA-8(8) Secure Evolvability
STATEMENT: >>>
Implement the security design principle of secure evolvability in [systems or system components].
<<<
BASELINE: None
STATUS: Draft

[REQUIREMENT]
UID: SA-8.9
TITLE: SA-8(9) Trusted Components
STATEMENT: >>>
Implement the security design principle of trusted components in [systems or system components].
<<<
BASELINE: None
STATUS: Draft

[REQUIREMENT]
UID: SA-8.10
TITLE: SA-8(10) Hierarchical Trust
STATEMENT: >>>
Implement the security design principle of hierarchical trust in [systems or system components].
<<<
BASELINE: None
STATUS: Draft

[REQUIREMENT]
UID: SA-8.11
TITLE: SA-8(11) Inverse Modification Threshold
STATEMENT: >>>
Implement the security design principle of inverse modification threshold in [systems or system components].
<<<
BASELINE: None
STATUS: Draft

[REQUIREMENT]
UID: SA-8.12
TITLE: SA-8(12) Hierarchical Protection
STATEMENT: >>>
Implement the security design principle of hierarchical protection in [systems or system components].
<<<
BASELINE: None
STATUS: Draft

[REQUIREMENT]
UID: SA-8.13
TITLE: SA-8(13) Minimized Security Elements
STATEMENT: >>>
Implement the security design principle of minimized security elements in [systems or system components].
<<<
BASELINE: None
STATUS: Draft

[REQUIREMENT]
UID: SA-8.14
TITLE: SA-8(14) Least Privilege
STATEMENT: >>>
Implement the security design principle of least privilege in [systems or system components].
<<<
BASELINE: None
STATUS: Draft

[REQUIREMENT]
UID: SA-8.15
TITLE: SA-8(15) Predicate Permission
STATEMENT: >>>
Implement the security design principle of predicate permission in [systems or system components].
<<<
BASELINE: None
STATUS: Draft

[REQUIREMENT]
UID: SA-8.16
TITLE: SA-8(16) Self-reliant Trustworthiness
STATEMENT: >>>
Implement the security design principle of self-reliant trustworthiness in [systems or system components].
<<<
BASELINE: None
STATUS: Draft

[REQUIREMENT]
UID: SA-8.17
TITLE: SA-8(17) Secure Distributed Composition
STATEMENT: >>>
Implement the security design principle of secure distributed composition in [systems or system components].
<<<
BASELINE: None
STATUS: Draft

[REQUIREMENT]
UID: SA-8.18
TITLE: SA-8(18) Trusted Communications Channels
STATEMENT: >>>
Implement the security design principle of trusted communications channels in [systems or system components].
<<<
BASELINE: None
STATUS: Draft

[REQUIREMENT]
UID: SA-8.19
TITLE: SA-8(19) Continuous Protection
STATEMENT: >>>
Implement the security design principle of continuous protection in [systems or system components].
<<<
BASELINE: None
STATUS: Draft

[REQUIREMENT]
UID: SA-8.20
TITLE: SA-8(20) Secure Metadata Management
STATEMENT: >>>
Implement the security design principle of secure metadata management in [systems or system components].
<<<
BASELINE: None
STATUS: Draft

[REQUIREMENT]
UID: SA-8.21
TITLE: SA-8(21) Self-analysis
STATEMENT: >>>
Implement the security design principle of self-analysis in [systems or system components].
<<<
BASELINE: None
STATUS: Draft

[REQUIREMENT]
UID: SA-8.22
TITLE: SA-8(22) Accountability and Traceability
STATEMENT: >>>
Implement the security design principle of accountability and traceability in [organization-defined systems or system components].
<<<
BASELINE: None
STATUS: Draft

[REQUIREMENT]
UID: SA-8.23
TITLE: SA-8(23) Secure Defaults
STATEMENT: >>>
Implement the security design principle of secure defaults in [systems or system components].
<<<
BASELINE: None
STATUS: Draft

[REQUIREMENT]
UID: SA-8.24
TITLE: SA-8(24) Secure Failure and Recovery
STATEMENT: >>>
Implement the security design principle of secure failure and recovery in [organization-defined systems or system components].
<<<
BASELINE: None
STATUS: Draft

[REQUIREMENT]
UID: SA-8.25
TITLE: SA-8(25) Economic Security
STATEMENT: >>>
Implement the security design principle of economic security in [systems or system components].
<<<
BASELINE: None
STATUS: Draft

[REQUIREMENT]
UID: SA-8.26
TITLE: SA-8(26) Performance Security
STATEMENT: >>>
Implement the security design principle of performance security in [systems or system components].
<<<
BASELINE: None
STATUS: Draft

[REQUIREMENT]
UID: SA-8.27
TITLE: SA-8(27) Human Factored Security
STATEMENT: >>>
Implement the security design principle of human factored security in [systems or system components].
<<<
BASELINE: None
STATUS: Draft

[REQUIREMENT]
UID: SA-8.28
TITLE: SA-8(28) Acceptable Security
STATEMENT: >>>
Implement the security design principle of acceptable security in [systems or system components].
<<<
BASELINE: None
STATUS: Draft

[REQUIREMENT]
UID: SA-8.29
TITLE: SA-8(29) Repeatable and Documented Procedures
STATEMENT: >>>
Implement the security design principle of repeatable and documented procedures in [systems or system components].
<<<
BASELINE: None
STATUS: Draft

[REQUIREMENT]
UID: SA-8.30
TITLE: SA-8(30) Procedural Rigor
STATEMENT: >>>
Implement the security design principle of procedural rigor in [systems or system components].
<<<
BASELINE: None
STATUS: Draft

[REQUIREMENT]
UID: SA-8.31
TITLE: SA-8(31) Secure System Modification
STATEMENT: >>>
Implement the security design principle of secure system modification in [systems or system components].
<<<
BASELINE: None
STATUS: Draft

[REQUIREMENT]
UID: SA-8.32
TITLE: SA-8(32) Sufficient Documentation
STATEMENT: >>>
Implement the security design principle of sufficient documentation in [systems or system components].
<<<
BASELINE: None
STATUS: Draft

[REQUIREMENT]
UID: SA-8.33
TITLE: SA-8(33) Minimization
STATEMENT: >>>
Implement the privacy principle of minimization using [processes].
<<<
COMMENT: Baselines: Privacy
BASELINE: Privacy
STATUS: Draft

[REQUIREMENT]
UID: SA-9
TITLE: SA-9 External System Services
STATEMENT: >>>
a. Require that providers of external system services comply with organizational security and privacy requirements and employ the following controls: [controls];

b. Define and document organizational oversight and user roles and responsibilities with regard to external system services; and

c. Employ the following processes, methods, and techniques to monitor control compliance by external service providers on an ongoing basis: [processes, methods, and techniques].
<<<
COMMENT: Baselines: Low, Moderate, High, Privacy
BASELINE: Low
STATUS: Draft

[REQUIREMENT]
UID: SA-9.1
TITLE: SA-9(1) Risk Assessments and Organizational Approvals
STATEMENT: >>>
(a) Conduct an organizational assessment of risk prior to the acquisition or outsourcing of information security services; and

(b) Verify that the acquisition or outsourcing of dedicated information security services is approved by [personnel or roles].
<<<
BASELINE: None
STATUS: Draft

[REQUIREMENT]
UID: SA-9.2
TITLE: SA-9(2) Identification of Functions, Ports, Protocols, and Services
STATEMENT: >>>
Require providers of the following external system services to identify the functions, ports, protocols, and other services required for the use of such services: [external system services].
<<<
COMMENT: Baselines: Moderate, High
BASELINE: Moderate
STATUS: Draft

[REQUIREMENT]
UID: SA-9.3
TITLE: SA-9(3) Establish and Maintain Trust Relationship with Providers
STATEMENT: >>>
Establish, document, and maintain trust relationships with external service providers based on the following requirements, properties, factors, or conditions: [organization-defined security and privacy requirements, properties, factors, or conditions defining acceptable trust relationships].
<<<
BASELINE: None
STATUS: Draft

[REQUIREMENT]
UID: SA-9.4
TITLE: SA-9(4) Consistent Interests of Consumers and Providers
STATEMENT: >>>
Take the following actions to verify that the interests of [external service providers] are consistent with and reflect organizational interests: [actions].
<<<
BASELINE: None
STATUS: Draft

[REQUIREMENT]
UID: SA-9.5
TITLE: SA-9(5) Processing, Storage, and Service Location
STATEMENT: >>>
Restrict the location of [sa-09.05_odp.01] to [locations] based on [requirements].
<<<
BASELINE: None
STATUS: Draft

[REQUIREMENT]
UID: SA-9.6
TITLE: SA-9(6) Organization-controlled Cryptographic Keys
STATEMENT: >>>
Maintain exclusive control of cryptographic keys for encrypted material stored or transmitted through an external system.
<<<
BASELINE: None
STATUS: Draft

[REQUIREMENT]
UID: SA-9.7
TITLE: SA-9(7) Organization-controlled Integrity Checking
STATEMENT: >>>
Provide the capability to check the integrity of information while it resides in the external system.
<<<
BASELINE: None
STATUS: Draft

[REQUIREMENT]
UID: SA-9.8
TITLE: SA-9(8) Processing and Storage Location — U.S. Jurisdiction
STATEMENT: >>>
Restrict the geographic location of information processing and data storage to facilities located within in the legal jurisdictional boundary of the United States.
<<<
BASELINE: None
STATUS: Draft

[REQUIREMENT]
UID: SA-10
TITLE: SA-10 Developer Configuration Management
STATEMENT: >>>
Require the developer of the system, system component, or system service to:

  a. Perform configuration management during system, component, or service [sa-10_odp.01];

  b. Document, manage, and control the integrity of changes to [configuration items];

  c. Implement only organization-approved changes to the system, component, or service;

  d. Document approved changes to the system, component, or service and the potential security and privacy impacts of such changes; and

  e. Track security flaws and flaw resolution within the system, component, or service and report findings to [personnel].
<<<
COMMENT: Baselines: Moderate, High
BASELINE: Moderate
STATUS: Draft

[REQUIREMENT]
UID: SA-10.1
TITLE: SA-10(1) Software and Firmware Integrity Verification
STATEMENT: >>>
Require the developer of the system, system component, or system service to enable integrity verification of software and firmware components.
<<<
BASELINE: None
STATUS: Draft

[REQUIREMENT]
UID: SA-10.2
TITLE: SA-10(2) Alternative Configuration Management Processes
STATEMENT: >>>
Provide an alternate configuration management process using organizational personnel in the absence of a dedicated developer configuration management team.
<<<
BASELINE: None
STATUS: Draft

[REQUIREMENT]
UID: SA-10.3
TITLE: SA-10(3) Hardware Integrity Verification
STATEMENT: >>>
Require the developer of the system, system component, or system service to enable integrity verification of hardware components.
<<<
BASELINE: None
STATUS: Draft

[REQUIREMENT]
UID: SA-10.4
TITLE: SA-10(4) Trusted Generation
STATEMENT: >>>
Require the developer of the system, system component, or system service to employ tools for comparing newly generated versions of security-relevant hardware descriptions, source code, and object code with previous versions.
<<<
BASELINE: None
STATUS: Draft

[REQUIREMENT]
UID: SA-10.5
TITLE: SA-10(5) Mapping Integrity for Version Control
STATEMENT: >>>
Require the developer of the system, system component, or system service to maintain the integrity of the mapping between the master build data describing the current version of security-relevant hardware, software, and firmware and the on-site master copy of the data for the current version.
<<<
BASELINE: None
STATUS: Draft

[REQUIREMENT]
UID: SA-10.6
TITLE: SA-10(6) Trusted Distribution
STATEMENT: >>>
Require the developer of the system, system component, or system service to execute procedures for ensuring that security-relevant hardware, software, and firmware updates distributed to the organization are exactly as specified by the master copies.
<<<
BASELINE: None
STATUS: Draft

[REQUIREMENT]
UID: SA-10.7
TITLE: SA-10(7) Security and Privacy Representatives
STATEMENT: >>>
Require [organization-defined security and privacy representatives] to be included in the [organization-defined configuration change management and control process].
<<<
BASELINE: None
STATUS: Draft

[REQUIREMENT]
UID: SA-11
TITLE: SA-11 Developer Testing and Evaluation
STATEMENT: >>>
Require the developer of the system, system component, or system service, at all post-design stages of the system development life cycle, to:

  a. Develop and implement a plan for ongoing security and privacy control assessments;

  b. Perform [sa-11_odp.01] testing/evaluation [frequency to conduct] at [depth and coverage];

  c. Produce evidence of the execution of the assessment plan and the results of the testing and evaluation;

  d. Implement a verifiable flaw remediation process; and

  e. Correct flaws identified during testing and evaluation.
<<<
COMMENT: Baselines: Moderate, High, Privacy
BASELINE: Moderate
STATUS: Draft

[REQUIREMENT]
UID: SA-11.1
TITLE: SA-11(1) Static Code Analysis
STATEMENT: >>>
Require the developer of the system, system component, or system service to employ static code analysis tools to identify common flaws and document the results of the analysis.
<<<
BASELINE: None
STATUS: Draft

[REQUIREMENT]
UID: SA-11.2
TITLE: SA-11(2) Threat Modeling and Vulnerability Analyses
STATEMENT: >>>
Require the developer of the system, system component, or system service to perform threat modeling and vulnerability analyses during development and the subsequent testing and evaluation of the system, component, or service that:

  (a) Uses the following contextual information: [information];

  (b) Employs the following tools and methods: [tools and methods];

  (c) Conducts the modeling and analyses at the following level of rigor: [organization-defined breadth and depth of modeling and analyses] ; and

  (d) Produces evidence that meets the following acceptance criteria: [organization-defined acceptance criteria].
<<<
BASELINE: None
STATUS: Draft

[REQUIREMENT]
UID: SA-11.3
TITLE: SA-11(3) Independent Verification of Assessment Plans and Evidence
STATEMENT: >>>
(a) Require an independent agent satisfying [independence criteria] to verify the correct implementation of the developer security and privacy assessment plans and the evidence produced during testing and evaluation; and

(b) Verify that the independent agent is provided with sufficient information to complete the verification process or granted the authority to obtain such information.
<<<
BASELINE: None
STATUS: Draft

[REQUIREMENT]
UID: SA-11.4
TITLE: SA-11(4) Manual Code Reviews
STATEMENT: >>>
Require the developer of the system, system component, or system service to perform a manual code review of [specific code] using the following processes, procedures, and/or techniques: [processes, procedures, and/or techniques].
<<<
BASELINE: None
STATUS: Draft

[REQUIREMENT]
UID: SA-11.5
TITLE: SA-11(5) Penetration Testing
STATEMENT: >>>
Require the developer of the system, system component, or system service to perform penetration testing:

  (a) At the following level of rigor: [organization-defined breadth and depth of testing] ; and

  (b) Under the following constraints: [constraints].
<<<
BASELINE: None
STATUS: Draft

[REQUIREMENT]
UID: SA-11.6
TITLE: SA-11(6) Attack Surface Reviews
STATEMENT: >>>
Require the developer of the system, system component, or system service to perform attack surface reviews.
<<<
BASELINE: None
STATUS: Draft

[REQUIREMENT]
UID: SA-11.7
TITLE: SA-11(7) Verify Scope of Testing and Evaluation
STATEMENT: >>>
Require the developer of the system, system component, or system service to verify that the scope of testing and evaluation provides complete coverage of the required controls at the following level of rigor: [organization-defined breadth and depth of testing and evaluation].
<<<
BASELINE: None
STATUS: Draft

[REQUIREMENT]
UID: SA-11.8
TITLE: SA-11(8) Dynamic Code Analysis
STATEMENT: >>>
Require the developer of the system, system component, or system service to employ dynamic code analysis tools to identify common flaws and document the results of the analysis.
<<<
BASELINE: None
STATUS: Draft

[REQUIREMENT]
UID: SA-11.9
TITLE: SA-11(9) Interactive Application Security Testing
STATEMENT: >>>
Require the developer of the system, system component, or system service to employ interactive application security testing tools to identify flaws and document the results.
<<<
BASELINE: None
STATUS: Draft

[REQUIREMENT]
UID: SA-12
TITLE: SA-12 Supply Chain Protection
STATEMENT: >>>
Withdrawn. Incorporated into SR.
<<<
COMMENT: Withdrawn
BASELINE: None
STATUS: Draft

[REQUIREMENT]
UID: SA-12.1
TITLE: SA-12(1) Acquisition Strategies / Tools / Methods
STATEMENT: >>>
Withdrawn.
<<<
COMMENT: Withdrawn
BASELINE: None
STATUS: Draft

[REQUIREMENT]
UID: SA-12.2
TITLE: SA-12(2) Supplier Reviews
STATEMENT: >>>
Withdrawn.
<<<
COMMENT: Withdrawn
BASELINE: None
STATUS: Draft

[REQUIREMENT]
UID: SA-12.3
TITLE: SA-12(3) Trusted Shipping and Warehousing
STATEMENT: >>>
Withdrawn. Incorporated into SR-3.
<<<
COMMENT: Withdrawn
BASELINE: None
STATUS: Draft

[REQUIREMENT]
UID: SA-12.4
TITLE: SA-12(4) Diversity of Suppliers
STATEMENT: >>>
Withdrawn.
<<<
COMMENT: Withdrawn
BASELINE: None
STATUS: Draft

[REQUIREMENT]
UID: SA-12.5
TITLE: SA-12(5) Limitation of Harm
STATEMENT: >>>
Withdrawn.
<<<
COMMENT: Withdrawn
BASELINE: None
STATUS: Draft

[REQUIREMENT]
UID: SA-12.6
TITLE: SA-12(6) Minimizing Procurement Time
STATEMENT: >>>
Withdrawn. Incorporated into SR-5.1.
<<<
COMMENT: Withdrawn
BASELINE: None
STATUS: Draft

[REQUIREMENT]
UID: SA-12.7
TITLE: SA-12(7) Assessments Prior to Selection / Acceptance / Update
STATEMENT: >>>
Withdrawn.
<<<
COMMENT: Withdrawn
BASELINE: None
STATUS: Draft

[REQUIREMENT]
UID: SA-12.8
TITLE: SA-12(8) Use of All-source Intelligence
STATEMENT: >>>
Withdrawn. Incorporated into RA-3.2.
<<<
COMMENT: Withdrawn
BASELINE: None
STATUS: Draft

[REQUIREMENT]
UID: SA-12.9
TITLE: SA-12(9) Operations Security
STATEMENT: >>>
Withdrawn.
<<<
COMMENT: Withdrawn
BASELINE: None
STATUS: Draft

[REQUIREMENT]
UID: SA-12.10
TITLE: SA-12(10) Validate as Genuine and Not Altered
STATEMENT: >>>
Withdrawn.
<<<
COMMENT: Withdrawn
BASELINE: None
STATUS: Draft

[REQUIREMENT]
UID: SA-12.11
TITLE: SA-12(11) Penetration Testing / Analysis of Elements, Processes, and Actors
STATEMENT: >>>
Withdrawn.
<<<
COMMENT: Withdrawn
BASELINE: None
STATUS: Draft

[REQUIREMENT]
UID: SA-12.12
TITLE: SA-12(12) Inter-organizational Agreements
STATEMENT: >>>
Withdrawn.
<<<
COMMENT: Withdrawn
BASELINE: None
STATUS: Draft

[REQUIREMENT]
UID: SA-12.13
TITLE: SA-12(13) Critical Information System Components
STATEMENT: >>>
Withdrawn. Incorporated into MA-6, RA-9.
<<<
COMMENT: Withdrawn
BASELINE: None
STATUS: Draft

[REQUIREMENT]
UID: SA-12.14
TITLE: SA-12(14) Identity and Traceability
STATEMENT: >>>
Withdrawn. Incorporated into SR-4.1, SR-4.2.
<<<
COMMENT: Withdrawn
BASELINE: None
STATUS: Draft

[REQUIREMENT]
UID: SA-12.15
TITLE: SA-12(15) Processes to Address Weaknesses or Deficiencies
STATEMENT: >>>
Withdrawn. Incorporated into SR-3.
<<<
COMMENT: Withdrawn
BASELINE: None
STATUS: Draft

[REQUIREMENT]
UID: SA-13
TITLE: SA-13 Trustworthiness
STATEMENT: >>>
Withdrawn. Incorporated into SA-8.
<<<
COMMENT: Withdrawn
BASELINE: None
STATUS: Draft

[REQUIREMENT]
UID: SA-14
TITLE: SA-14 Criticality Analysis
STATEMENT: >>>
Withdrawn. Incorporated into RA-9.
<<<
COMMENT: Withdrawn
BASELINE: None
STATUS: Draft

[REQUIREMENT]
UID: SA-14.1
TITLE: SA-14(1) Critical Components with No Viable Alternative Sourcing
STATEMENT: >>>
Withdrawn. Incorporated into SA-20.
<<<
COMMENT: Withdrawn
BASELINE: None
STATUS: Draft

[REQUIREMENT]
UID: SA-15
TITLE: SA-15 Development Process, Standards, and Tools
STATEMENT: >>>
a. Require the developer of the system, system component, or system service to follow a documented development process that:

  1. Explicitly addresses security and privacy requirements;

  2. Identifies the standards and tools used in the development process;

  3. Documents the specific tool options and tool configurations used in the development process; and

  4. Documents, manages, and ensures the integrity of changes to the process and/or tools used in development; and

b. Review the development process, standards, tools, tool options, and tool configurations [frequency] to determine if the process, standards, tools, tool options and tool configurations selected and employed can satisfy the following security and privacy requirements: [organization-defined security and privacy requirements].
<<<
COMMENT: Baselines: Moderate, High
BASELINE: Moderate
STATUS: Draft

[REQUIREMENT]
UID: SA-15.1
TITLE: SA-15(1) Quality Metrics
STATEMENT: >>>
Require the developer of the system, system component, or system service to:

  (a) Define quality metrics at the beginning of the development process; and

  (b) Provide evidence of meeting the quality metrics [sa-15.01_odp.01].
<<<
BASELINE: None
STATUS: Draft

[REQUIREMENT]
UID: SA-15.2
TITLE: SA-15(2) Security and Privacy Tracking Tools
STATEMENT: >>>
Require the developer of the system, system component, or system service to select and employ security and privacy tracking tools for use during the development process.
<<<
BASELINE: None
STATUS: Draft

[REQUIREMENT]
UID: SA-15.3
TITLE: SA-15(3) Criticality Analysis
STATEMENT: >>>
Require the developer of the system, system component, or system service to perform a criticality analysis:

  (a) At the following decision points in the system development life cycle: [decision points] ; and

  (b) At the following level of rigor: [organization-defined breadth and depth of criticality analysis].
<<<
COMMENT: Baselines: Moderate, High
BASELINE: Moderate
STATUS: Draft

[REQUIREMENT]
UID: SA-15.4
TITLE: SA-15(4) Threat Modeling and Vulnerability Analysis
STATEMENT: >>>
Withdrawn. Incorporated into SA-11.2.
<<<
COMMENT: Withdrawn
BASELINE: None
STATUS: Draft

[REQUIREMENT]
UID: SA-15.5
TITLE: SA-15(5) Attack Surface Reduction
STATEMENT: >>>
Require the developer of the system, system component, or system service to reduce attack surfaces to [thresholds].
<<<
BASELINE: None
STATUS: Draft

[REQUIREMENT]
UID: SA-15.6
TITLE: SA-15(6) Continuous Improvement
STATEMENT: >>>
Require the developer of the system, system component, or system service to implement an explicit process to continuously improve the development process.
<<<
BASELINE: None
STATUS: Draft

[REQUIREMENT]
UID: SA-15.7
TITLE: SA-15(7) Automated Vulnerability Analysis
STATEMENT: >>>
Require the developer of the system, system component, or system service [frequency] to:

  (a) Perform an automated vulnerability analysis using [tools];

  (b) Determine the exploitation potential for discovered vulnerabilities;

  (c) Determine potential risk mitigations for delivered vulnerabilities; and

  (d) Deliver the outputs of the tools and results of the analysis to [personnel or roles].
<<<
BASELINE: None
STATUS: Draft

[REQUIREMENT]
UID: SA-15.8
TITLE: SA-15(8) Reuse of Threat and Vulnerability Information
STATEMENT: >>>
Require the developer of the system, system component, or system service to use threat modeling and vulnerability analyses from similar systems, components, or services to inform the current development process.
<<<
BASELINE: None
STATUS: Draft

[REQUIREMENT]
UID: SA-15.9
TITLE: SA-15(9) Use of Live Data
STATEMENT: >>>
Withdrawn. Incorporated into SA-3.2.
<<<
COMMENT: Withdrawn
BASELINE: None
STATUS: Draft

[REQUIREMENT]
UID: SA-15.10
TITLE: SA-15(10) Incident Response Plan
STATEMENT: >>>
Require the developer of the system, system component, or system service to provide, implement, and test an incident response plan.
<<<
BASELINE: None
STATUS: Draft

[REQUIREMENT]
UID: SA-15.11
TITLE: SA-15(11) Archive System or Component
STATEMENT: >>>
Require the developer of the system or system component to archive the system or component to be released or delivered together with the corresponding evidence supporting the final security and privacy review.
<<<
BASELINE: None
STATUS: Draft

[REQUIREMENT]
UID: SA-15.12
TITLE: SA-15(12) Minimize Personally Identifiable Information
STATEMENT: >>>
Require the developer of the system or system component to minimize the use of personally identifiable information in development and test environments.
<<<
BASELINE: None
STATUS: Draft

[REQUIREMENT]
UID: SA-15.13
TITLE: SA-15(13) Logging Syntax
STATEMENT: >>>
Require the developer of the system or system component to minimize the use of personally identifiable information in development and test environments.
<<<
BASELINE: None
STATUS: Draft

[REQUIREMENT]
UID: SA-16
TITLE: SA-16 Developer-provided Training
STATEMENT: >>>
Require the developer of the system, system component, or system service to provide the following training on the correct use and operation of the implemented security and privacy functions, controls, and/or mechanisms: [training].
<<<
COMMENT: Baselines: High
BASELINE: High
STATUS: Draft

[REQUIREMENT]
UID: SA-17
TITLE: SA-17 Developer Security and Privacy Architecture and Design
STATEMENT: >>>
Require the developer of the system, system component, or system service to produce a design specification and security and privacy architecture that:

  a. Is consistent with the organization’s security and privacy architecture that is an integral part the organization’s enterprise architecture;

  b. Accurately and completely describes the required security and privacy functionality, and the allocation of controls among physical and logical components; and

  c. Expresses how individual security and privacy functions, mechanisms, and services work together to provide required security and privacy capabilities and a unified approach to protection.
<<<
COMMENT: Baselines: High
BASELINE: High
STATUS: Draft

[REQUIREMENT]
UID: SA-17.1
TITLE: SA-17(1) Formal Policy Model
STATEMENT: >>>
Require the developer of the system, system component, or system service to:

  (a) Produce, as an integral part of the development process, a formal policy model describing the [organization-defined elements of organizational security and privacy policy] to be enforced; and

  (b) Prove that the formal policy model is internally consistent and sufficient to enforce the defined elements of the organizational security and privacy policy when implemented.
<<<
BASELINE: None
STATUS: Draft

[REQUIREMENT]
UID: SA-17.2
TITLE: SA-17(2) Security-relevant Components
STATEMENT: >>>
Require the developer of the system, system component, or system service to:

  (a) Define security-relevant hardware, software, and firmware; and

  (b) Provide a rationale that the definition for security-relevant hardware, software, and firmware is complete.
<<<
BASELINE: None
STATUS: Draft

[REQUIREMENT]
UID: SA-17.3
TITLE: SA-17(3) Formal Correspondence
STATEMENT: >>>
Require the developer of the system, system component, or system service to:

  (a) Produce, as an integral part of the development process, a formal top-level specification that specifies the interfaces to security-relevant hardware, software, and firmware in terms of exceptions, error messages, and effects;

  (b) Show via proof to the extent feasible with additional informal demonstration as necessary, that the formal top-level specification is consistent with the formal policy model;

  (c) Show via informal demonstration, that the formal top-level specification completely covers the interfaces to security-relevant hardware, software, and firmware;

  (d) Show that the formal top-level specification is an accurate description of the implemented security-relevant hardware, software, and firmware; and

  (e) Describe the security-relevant hardware, software, and firmware mechanisms not addressed in the formal top-level specification but strictly internal to the security-relevant hardware, software, and firmware.
<<<
BASELINE: None
STATUS: Draft

[REQUIREMENT]
UID: SA-17.4
TITLE: SA-17(4) Informal Correspondence
STATEMENT: >>>
Require the developer of the system, system component, or system service to:

  (a) Produce, as an integral part of the development process, an informal descriptive top-level specification that specifies the interfaces to security-relevant hardware, software, and firmware in terms of exceptions, error messages, and effects;

  (b) Show via [sa-17.04_odp] that the descriptive top-level specification is consistent with the formal policy model;

  (c) Show via informal demonstration, that the descriptive top-level specification completely covers the interfaces to security-relevant hardware, software, and firmware;

  (d) Show that the descriptive top-level specification is an accurate description of the interfaces to security-relevant hardware, software, and firmware; and

  (e) Describe the security-relevant hardware, software, and firmware mechanisms not addressed in the descriptive top-level specification but strictly internal to the security-relevant hardware, software, and firmware.
<<<
BASELINE: None
STATUS: Draft

[REQUIREMENT]
UID: SA-17.5
TITLE: SA-17(5) Conceptually Simple Design
STATEMENT: >>>
Require the developer of the system, system component, or system service to:

  (a) Design and structure the security-relevant hardware, software, and firmware to use a complete, conceptually simple protection mechanism with precisely defined semantics; and

  (b) Internally structure the security-relevant hardware, software, and firmware with specific regard for this mechanism.
<<<
BASELINE: None
STATUS: Draft

[REQUIREMENT]
UID: SA-17.6
TITLE: SA-17(6) Structure for Testing
STATEMENT: >>>
Require the developer of the system, system component, or system service to structure security-relevant hardware, software, and firmware to facilitate testing.
<<<
BASELINE: None
STATUS: Draft

[REQUIREMENT]
UID: SA-17.7
TITLE: SA-17(7) Structure for Least Privilege
STATEMENT: >>>
Require the developer of the system, system component, or system service to structure security-relevant hardware, software, and firmware to facilitate controlling access with least privilege.
<<<
BASELINE: None
STATUS: Draft

[REQUIREMENT]
UID: SA-17.8
TITLE: SA-17(8) Orchestration
STATEMENT: >>>
Design [critical systems] with coordinated behavior to implement the following capabilities: [capabilities].
<<<
BASELINE: None
STATUS: Draft

[REQUIREMENT]
UID: SA-17.9
TITLE: SA-17(9) Design Diversity
STATEMENT: >>>
Use different designs for [critical systems] to satisfy a common set of requirements or to provide equivalent functionality.
<<<
BASELINE: None
STATUS: Draft

[REQUIREMENT]
UID: SA-18
TITLE: SA-18 Tamper Resistance and Detection
STATEMENT: >>>
Withdrawn.
<<<
COMMENT: Withdrawn
BASELINE: None
STATUS: Draft

[REQUIREMENT]
UID: SA-18.1
TITLE: SA-18(1) Multiple Phases of System Development Life Cycle
STATEMENT: >>>
Withdrawn.
<<<
COMMENT: Withdrawn
BASELINE: None
STATUS: Draft

[REQUIREMENT]
UID: SA-18.2
TITLE: SA-18(2) Inspection of Systems or Components
STATEMENT: >>>
Withdrawn.
<<<
COMMENT: Withdrawn
BASELINE: None
STATUS: Draft

[REQUIREMENT]
UID: SA-19
TITLE: SA-19 Component Authenticity
STATEMENT: >>>
Withdrawn.
<<<
COMMENT: Withdrawn
BASELINE: None
STATUS: Draft

[REQUIREMENT]
UID: SA-19.1
TITLE: SA-19(1) Anti-counterfeit Training
STATEMENT: >>>
Withdrawn.
<<<
COMMENT: Withdrawn
BASELINE: None
STATUS: Draft

[REQUIREMENT]
UID: SA-19.2
TITLE: SA-19(2) Configuration Control for Component Service and Repair
STATEMENT: >>>
Withdrawn.
<<<
COMMENT: Withdrawn
BASELINE: None
STATUS: Draft

[REQUIREMENT]
UID: SA-19.3
TITLE: SA-19(3) Component Disposal
STATEMENT: >>>
Withdrawn.
<<<
COMMENT: Withdrawn
BASELINE: None
STATUS: Draft

[REQUIREMENT]
UID: SA-19.4
TITLE: SA-19(4) Anti-counterfeit Scanning
STATEMENT: >>>
Withdrawn.
<<<
COMMENT: Withdrawn
BASELINE: None
STATUS: Draft

[REQUIREMENT]
UID: SA-20
TITLE: SA-20 Customized Development of Critical Components
STATEMENT: >>>
Reimplement or custom develop the following critical system components: [critical system].
<<<
BASELINE: None
STATUS: Draft

[REQUIREMENT]
UID: SA-21
TITLE: SA-21 Developer Screening
STATEMENT: >>>
Require that the developer of [system, systems component, or system service]:

  a. Has appropriate access authorizations as determined by assigned [official government duties] ; and

  b. Satisfies the following additional personnel screening criteria: [additional personnel screening criteria].
<<<
COMMENT: Baselines: High
BASELINE: High
STATUS: Draft

[REQUIREMENT]
UID: SA-21.1
TITLE: SA-21(1) Validation of Screening
STATEMENT: >>>
Withdrawn. Incorporated into SA-21.
<<<
COMMENT: Withdrawn
BASELINE: None
STATUS: Draft

[REQUIREMENT]
UID: SA-22
TITLE: SA-22 Unsupported System Components
STATEMENT: >>>
a. Replace system components when support for the components is no longer available from the developer, vendor, or manufacturer; or

b. Provide the following options for alternative sources for continued support for unsupported components [sa-22_odp.01].
<<<
COMMENT: Baselines: Low, Moderate, High
BASELINE: Low
STATUS: Draft

[REQUIREMENT]
UID: SA-22.1
TITLE: SA-22(1) Alternative Sources for Continued Support
STATEMENT: >>>
Withdrawn. Incorporated into SA-22.
<<<
COMMENT: Withdrawn
BASELINE: None
STATUS: Draft

[REQUIREMENT]
UID: SA-23
TITLE: SA-23 Specialization
STATEMENT: >>>
Employ [sa-23_odp.01] on [systems or system components] supporting mission essential services or functions to increase the trustworthiness in those systems or components.
<<<
BASELINE: None
STATUS: Draft

[REQUIREMENT]
UID: SA-24
TITLE: SA-24 Design For Cyber Resiliency
STATEMENT: >>>
a. Design organizational systems, system components, or system services to achieve cyber resiliency by:

  1. Defining the following cyber resiliency goals: [cyber resiliency goals].

  2. Defining the following cyber resiliency objectives: [cyber resiliency objectives].

  3. Defining the following cyber resiliency techniques: [cyber resiliency techniques].

  4. Defining the following cyber resiliency implementation approaches: [cyber resiliency implementation approaches].

  5. Defining the following cyber resiliency design principles: [cyber resiliency design principles].

b. Implement the selected cyber resiliency goals, objectives, techniques, implementation approaches, and design principles as part of an organizational risk management process or systems security engineering process.
<<<
BASELINE: None
STATUS: Draft

[[/SECTION]]

[[SECTION]]
UID: NIST-SC
TITLE: SC — System and Communications Protection

[REQUIREMENT]
UID: SC-1
TITLE: SC-1 Policy and Procedures
STATEMENT: >>>
a. Develop, document, and disseminate to [organization-defined personnel or roles]:

  1. [sc-01_odp.03] system and communications protection policy that:

    (a) Addresses purpose, scope, roles, responsibilities, management commitment, coordination among organizational entities, and compliance; and

    (b) Is consistent with applicable laws, executive orders, directives, regulations, policies, standards, and guidelines; and

  2. Procedures to facilitate the implementation of the system and communications protection policy and the associated system and communications protection controls;

b. Designate an [official] to manage the development, documentation, and dissemination of the system and communications protection policy and procedures; and

c. Review and update the current system and communications protection:

  1. Policy [frequency] and following [events] ; and

  2. Procedures [frequency] and following [events].
<<<
COMMENT: Baselines: Low, Moderate, High
BASELINE: Low
STATUS: Draft

[REQUIREMENT]
UID: SC-2
TITLE: SC-2 Separation of System and User Functionality
STATEMENT: >>>
Separate user functionality, including user interface services, from system management functionality.
<<<
COMMENT: Baselines: Moderate, High
BASELINE: Moderate
STATUS: Draft

[REQUIREMENT]
UID: SC-2.1
TITLE: SC-2(1) Interfaces for Non-privileged Users
STATEMENT: >>>
Prevent the presentation of system management functionality at interfaces to non-privileged users.
<<<
BASELINE: None
STATUS: Draft

[REQUIREMENT]
UID: SC-2.2
TITLE: SC-2(2) Disassociability
STATEMENT: >>>
Store state information from applications and software separately.
<<<
BASELINE: None
STATUS: Draft

[REQUIREMENT]
UID: SC-3
TITLE: SC-3 Security Function Isolation
STATEMENT: >>>
Isolate security functions from nonsecurity functions.
<<<
COMMENT: Baselines: High
BASELINE: High
STATUS: Draft

[REQUIREMENT]
UID: SC-3.1
TITLE: SC-3(1) Hardware Separation
STATEMENT: >>>
Employ hardware separation mechanisms to implement security function isolation.
<<<
BASELINE: None
STATUS: Draft

[REQUIREMENT]
UID: SC-3.2
TITLE: SC-3(2) Access and Flow Control Functions
STATEMENT: >>>
Isolate security functions enforcing access and information flow control from nonsecurity functions and from other security functions.
<<<
BASELINE: None
STATUS: Draft

[REQUIREMENT]
UID: SC-3.3
TITLE: SC-3(3) Minimize Nonsecurity Functionality
STATEMENT: >>>
Minimize the number of nonsecurity functions included within the isolation boundary containing security functions.
<<<
BASELINE: None
STATUS: Draft

[REQUIREMENT]
UID: SC-3.4
TITLE: SC-3(4) Module Coupling and Cohesiveness
STATEMENT: >>>
Implement security functions as largely independent modules that maximize internal cohesiveness within modules and minimize coupling between modules.
<<<
BASELINE: None
STATUS: Draft

[REQUIREMENT]
UID: SC-3.5
TITLE: SC-3(5) Layered Structures
STATEMENT: >>>
Implement security functions as a layered structure minimizing interactions between layers of the design and avoiding any dependence by lower layers on the functionality or correctness of higher layers.
<<<
BASELINE: None
STATUS: Draft

[REQUIREMENT]
UID: SC-4
TITLE: SC-4 Information in Shared System Resources
STATEMENT: >>>
Prevent unauthorized and unintended information transfer via shared system resources.
<<<
COMMENT: Baselines: Moderate, High
BASELINE: Moderate
STATUS: Draft

[REQUIREMENT]
UID: SC-4.1
TITLE: SC-4(1) Security Levels
STATEMENT: >>>
Withdrawn. Incorporated into SC-4.
<<<
COMMENT: Withdrawn
BASELINE: None
STATUS: Draft

[REQUIREMENT]
UID: SC-4.2
TITLE: SC-4(2) Multilevel or Periods Processing
STATEMENT: >>>
Prevent unauthorized information transfer via shared resources in accordance with [procedures] when system processing explicitly switches between different information classification levels or security categories.
<<<
BASELINE: None
STATUS: Draft

[REQUIREMENT]
UID: SC-5
TITLE: SC-5 Denial-of-service Protection
STATEMENT: >>>
a. [sc-05_odp.02] the effects of the following types of denial-of-service events: [types of denial-of-service events] ; and

b. Employ the following controls to achieve the denial-of-service objective: [controls by type of denial-of-service event].
<<<
COMMENT: Baselines: Low, Moderate, High
BASELINE: Low
STATUS: Draft

[REQUIREMENT]
UID: SC-5.1
TITLE: SC-5(1) Restrict Ability to Attack Other Systems
STATEMENT: >>>
Restrict the ability of individuals to launch the following denial-of-service attacks against other systems: [denial-of-service attacks].
<<<
BASELINE: None
STATUS: Draft

[REQUIREMENT]
UID: SC-5.2
TITLE: SC-5(2) Capacity, Bandwidth, and Redundancy
STATEMENT: >>>
Manage capacity, bandwidth, or other redundancy to limit the effects of information flooding denial-of-service attacks.
<<<
BASELINE: None
STATUS: Draft

[REQUIREMENT]
UID: SC-5.3
TITLE: SC-5(3) Detection and Monitoring
STATEMENT: >>>
(a) Employ the following monitoring tools to detect indicators of denial-of-service attacks against, or launched from, the system: [monitoring tools] ; and

(b) Monitor the following system resources to determine if sufficient resources exist to prevent effective denial-of-service attacks: [system resources].
<<<
BASELINE: None
STATUS: Draft

[REQUIREMENT]
UID: SC-6
TITLE: SC-6 Resource Availability
STATEMENT: >>>
Protect the availability of resources by allocating [resources] by [sc-06_odp.02].
<<<
BASELINE: None
STATUS: Draft

[REQUIREMENT]
UID: SC-7
TITLE: SC-7 Boundary Protection
STATEMENT: >>>
a. Monitor and control communications at the external managed interfaces to the system and at key internal managed interfaces within the system;

b. Implement subnetworks for publicly accessible system components that are [sc-07_odp] separated from internal organizational networks; and

c. Connect to external networks or systems only through managed interfaces consisting of boundary protection devices arranged in accordance with an organizational security and privacy architecture.
<<<
COMMENT: Baselines: Low, Moderate, High
BASELINE: Low
STATUS: Draft

[REQUIREMENT]
UID: SC-7.1
TITLE: SC-7(1) Physically Separated Subnetworks
STATEMENT: >>>
Withdrawn. Incorporated into SC-7.
<<<
COMMENT: Withdrawn
BASELINE: None
STATUS: Draft

[REQUIREMENT]
UID: SC-7.2
TITLE: SC-7(2) Public Access
STATEMENT: >>>
Withdrawn. Incorporated into SC-7.
<<<
COMMENT: Withdrawn
BASELINE: None
STATUS: Draft

[REQUIREMENT]
UID: SC-7.3
TITLE: SC-7(3) Access Points
STATEMENT: >>>
Limit the number of external network connections to the system.
<<<
COMMENT: Baselines: Moderate, High
BASELINE: Moderate
STATUS: Draft

[REQUIREMENT]
UID: SC-7.4
TITLE: SC-7(4) External Telecommunications Services
STATEMENT: >>>
(a) Implement a managed interface for each external telecommunication service;

(b) Establish a traffic flow policy for each managed interface;

(c) Protect the confidentiality and integrity of the information being transmitted across each interface;

(d) Document each exception to the traffic flow policy with a supporting mission or business need and duration of that need;

(e) Review exceptions to the traffic flow policy [frequency] and remove exceptions that are no longer supported by an explicit mission or business need;

(f) Prevent unauthorized exchange of control plane traffic with external networks;

(g) Publish information to enable remote networks to detect unauthorized control plane traffic from internal networks; and

(h) Filter unauthorized control plane traffic from external networks.
<<<
COMMENT: Baselines: Moderate, High
BASELINE: Moderate
STATUS: Draft

[REQUIREMENT]
UID: SC-7.5
TITLE: SC-7(5) Deny by Default — Allow by Exception
STATEMENT: >>>
Deny network communications traffic by default and allow network communications traffic by exception [sc-07.05_odp.01].
<<<
COMMENT: Baselines: Moderate, High
BASELINE: Moderate
STATUS: Draft

[REQUIREMENT]
UID: SC-7.6
TITLE: SC-7(6) Response to Recognized Failures
STATEMENT: >>>
Withdrawn. Incorporated into SC-7.18.
<<<
COMMENT: Withdrawn
BASELINE: None
STATUS: Draft

[REQUIREMENT]
UID: SC-7.7
TITLE: SC-7(7) Split Tunneling for Remote Devices
STATEMENT: >>>
Prevent split tunneling for remote devices connecting to organizational systems unless the split tunnel is securely provisioned using [safeguards].
<<<
COMMENT: Baselines: Moderate, High
BASELINE: Moderate
STATUS: Draft

[REQUIREMENT]
UID: SC-7.8
TITLE: SC-7(8) Route Traffic to Authenticated Proxy Servers
STATEMENT: >>>
Route [internal communications traffic] to [external networks] through authenticated proxy servers at managed interfaces.
<<<
COMMENT: Baselines: Moderate, High
BASELINE: Moderate
STATUS: Draft

[REQUIREMENT]
UID: SC-7.9
TITLE: SC-7(9) Restrict Threatening Outgoing Communications Traffic
STATEMENT: >>>
(a) Detect and deny outgoing communications traffic posing a threat to external systems; and

(b) Audit the identity of internal users associated with denied communications.
<<<
BASELINE: None
STATUS: Draft

[REQUIREMENT]
UID: SC-7.10
TITLE: SC-7(10) Prevent Exfiltration
STATEMENT: >>>
(a) Prevent the exfiltration of information; and

(b) Conduct exfiltration tests [frequency].
<<<
BASELINE: None
STATUS: Draft

[REQUIREMENT]
UID: SC-7.11
TITLE: SC-7(11) Restrict Incoming Communications Traffic
STATEMENT: >>>
Only allow incoming communications from [authorized sources] to be routed to [authorized destinations].
<<<
BASELINE: None
STATUS: Draft

[REQUIREMENT]
UID: SC-7.12
TITLE: SC-7(12) Host-based Protection
STATEMENT: >>>
Implement [host-based boundary protection mechanisms] at [system components].
<<<
BASELINE: None
STATUS: Draft

[REQUIREMENT]
UID: SC-7.13
TITLE: SC-7(13) Isolation of Security Tools, Mechanisms, and Support Components
STATEMENT: >>>
Isolate [information security tools, mechanisms, and support components] from other internal system components by implementing physically separate subnetworks with managed interfaces to other components of the system.
<<<
BASELINE: None
STATUS: Draft

[REQUIREMENT]
UID: SC-7.14
TITLE: SC-7(14) Protect Against Unauthorized Physical Connections
STATEMENT: >>>
Protect against unauthorized physical connections at [managed interfaces].
<<<
BASELINE: None
STATUS: Draft

[REQUIREMENT]
UID: SC-7.15
TITLE: SC-7(15) Networked Privileged Accesses
STATEMENT: >>>
Route networked, privileged accesses through a dedicated, managed interface for purposes of access control and auditing.
<<<
BASELINE: None
STATUS: Draft

[REQUIREMENT]
UID: SC-7.16
TITLE: SC-7(16) Prevent Discovery of System Components
STATEMENT: >>>
Prevent the discovery of specific system components that represent a managed interface.
<<<
BASELINE: None
STATUS: Draft

[REQUIREMENT]
UID: SC-7.17
TITLE: SC-7(17) Automated Enforcement of Protocol Formats
STATEMENT: >>>
Enforce adherence to protocol formats.
<<<
BASELINE: None
STATUS: Draft

[REQUIREMENT]
UID: SC-7.18
TITLE: SC-7(18) Fail Secure
STATEMENT: >>>
Prevent systems from entering unsecure states in the event of an operational failure of a boundary protection device.
<<<
COMMENT: Baselines: High
BASELINE: High
STATUS: Draft

[REQUIREMENT]
UID: SC-7.19
TITLE: SC-7(19) Block Communication from Non-organizationally Configured Hosts
STATEMENT: >>>
Block inbound and outbound communications traffic between [communication clients] that are independently configured by end users and external service providers.
<<<
BASELINE: None
STATUS: Draft

[REQUIREMENT]
UID: SC-7.20
TITLE: SC-7(20) Dynamic Isolation and Segregation
STATEMENT: >>>
Provide the capability to dynamically isolate [system components] from other system components.
<<<
BASELINE: None
STATUS: Draft

[REQUIREMENT]
UID: SC-7.21
TITLE: SC-7(21) Isolation of System Components
STATEMENT: >>>
Employ boundary protection mechanisms to isolate [system components] supporting [missions and/or business functions].
<<<
COMMENT: Baselines: High
BASELINE: High
STATUS: Draft

[REQUIREMENT]
UID: SC-7.22
TITLE: SC-7(22) Separate Subnets for Connecting to Different Security Domains
STATEMENT: >>>
Implement separate network addresses to connect to systems in different security domains.
<<<
BASELINE: None
STATUS: Draft

[REQUIREMENT]
UID: SC-7.23
TITLE: SC-7(23) Disable Sender Feedback on Protocol Validation Failure
STATEMENT: >>>
Disable feedback to senders on protocol format validation failure.
<<<
BASELINE: None
STATUS: Draft

[REQUIREMENT]
UID: SC-7.24
TITLE: SC-7(24) Personally Identifiable Information
STATEMENT: >>>
For systems that process personally identifiable information:

  (a) Apply the following processing rules to data elements of personally identifiable information: [processing rules];

  (b) Monitor for permitted processing at the external interfaces to the system and at key internal boundaries within the system;

  (c) Document each processing exception; and

  (d) Review and remove exceptions that are no longer supported.
<<<
COMMENT: Baselines: Privacy
BASELINE: Privacy
STATUS: Draft

[REQUIREMENT]
UID: SC-7.25
TITLE: SC-7(25) Unclassified National Security System Connections
STATEMENT: >>>
Prohibit the direct connection of [unclassified national security system] to an external network without the use of [boundary protection device].
<<<
BASELINE: None
STATUS: Draft

[REQUIREMENT]
UID: SC-7.26
TITLE: SC-7(26) Classified National Security System Connections
STATEMENT: >>>
Prohibit the direct connection of a classified national security system to an external network without the use of [boundary protection device].
<<<
BASELINE: None
STATUS: Draft

[REQUIREMENT]
UID: SC-7.27
TITLE: SC-7(27) Unclassified Non-national Security System Connections
STATEMENT: >>>
Prohibit the direct connection of [unclassified, non-national security system] to an external network without the use of [boundary protection device].
<<<
BASELINE: None
STATUS: Draft

[REQUIREMENT]
UID: SC-7.28
TITLE: SC-7(28) Connections to Public Networks
STATEMENT: >>>
Prohibit the direct connection of [system] to a public network.
<<<
BASELINE: None
STATUS: Draft

[REQUIREMENT]
UID: SC-7.29
TITLE: SC-7(29) Separate Subnets to Isolate Functions
STATEMENT: >>>
Implement [sc-07.29_odp.01] separate subnetworks to isolate the following critical system components and functions: [critical system components and functions].
<<<
BASELINE: None
STATUS: Draft

[REQUIREMENT]
UID: SC-8
TITLE: SC-8 Transmission Confidentiality and Integrity
STATEMENT: >>>
Protect the [sc-08_odp] of transmitted information.
<<<
COMMENT: Baselines: Moderate, High
BASELINE: Moderate
STATUS: Draft

[REQUIREMENT]
UID: SC-8.1
TITLE: SC-8(1) Cryptographic Protection
STATEMENT: >>>
Implement cryptographic mechanisms to [sc-08.01_odp] during transmission.
<<<
COMMENT: Baselines: Moderate, High
BASELINE: Moderate
STATUS: Draft

[REQUIREMENT]
UID: SC-8.2
TITLE: SC-8(2) Pre- and Post-transmission Handling
STATEMENT: >>>
Maintain the [sc-08.02_odp] of information during preparation for transmission and during reception.
<<<
BASELINE: None
STATUS: Draft

[REQUIREMENT]
UID: SC-8.3
TITLE: SC-8(3) Cryptographic Protection for Message Externals
STATEMENT: >>>
Implement cryptographic mechanisms to protect message externals unless otherwise protected by [alternative physical controls].
<<<
BASELINE: None
STATUS: Draft

[REQUIREMENT]
UID: SC-8.4
TITLE: SC-8(4) Conceal or Randomize Communications
STATEMENT: >>>
Implement cryptographic mechanisms to conceal or randomize communication patterns unless otherwise protected by [alternative physical controls].
<<<
BASELINE: None
STATUS: Draft

[REQUIREMENT]
UID: SC-8.5
TITLE: SC-8(5) Protected Distribution System
STATEMENT: >>>
Implement [protected distribution system] to [sc-08.05_odp.02] during transmission.
<<<
BASELINE: None
STATUS: Draft

[REQUIREMENT]
UID: SC-9
TITLE: SC-9 Transmission Confidentiality
STATEMENT: >>>
Withdrawn. Incorporated into SC-8.
<<<
COMMENT: Withdrawn
BASELINE: None
STATUS: Draft

[REQUIREMENT]
UID: SC-10
TITLE: SC-10 Network Disconnect
STATEMENT: >>>
Terminate the network connection associated with a communications session at the end of the session or after [time period] of inactivity.
<<<
COMMENT: Baselines: Moderate, High
BASELINE: Moderate
STATUS: Draft

[REQUIREMENT]
UID: SC-11
TITLE: SC-11 Trusted Path
STATEMENT: >>>
a. Provide a [sc-11_odp.01] isolated trusted communications path for communications between the user and the trusted components of the system; and

b. Permit users to invoke the trusted communications path for communications between the user and the following security functions of the system, including at a minimum, authentication and re-authentication: [security functions].
<<<
BASELINE: None
STATUS: Draft

[REQUIREMENT]
UID: SC-11.1
TITLE: SC-11(1) Irrefutable Communications Path
STATEMENT: >>>
(a) Provide a trusted communications path that is irrefutably distinguishable from other communications paths; and

(b) Initiate the trusted communications path for communications between the [security functions] of the system and the user.
<<<
BASELINE: None
STATUS: Draft

[REQUIREMENT]
UID: SC-12
TITLE: SC-12 Cryptographic Key Establishment and Management
STATEMENT: >>>
Establish and manage cryptographic keys when cryptography is employed within the system in accordance with the following key management requirements: [requirements].
<<<
COMMENT: Baselines: Low, Moderate, High
BASELINE: Low
STATUS: Draft

[REQUIREMENT]
UID: SC-12.1
TITLE: SC-12(1) Availability
STATEMENT: >>>
Maintain availability of information in the event of the loss of cryptographic keys by users.
<<<
COMMENT: Baselines: High
BASELINE: High
STATUS: Draft

[REQUIREMENT]
UID: SC-12.2
TITLE: SC-12(2) Symmetric Keys
STATEMENT: >>>
Produce, control, and distribute symmetric cryptographic keys using [sc-12.02_odp] key management technology and processes.
<<<
BASELINE: None
STATUS: Draft

[REQUIREMENT]
UID: SC-12.3
TITLE: SC-12(3) Asymmetric Keys
STATEMENT: >>>
Produce, control, and distribute asymmetric cryptographic keys using [sc-12.03_odp].
<<<
BASELINE: None
STATUS: Draft

[REQUIREMENT]
UID: SC-12.4
TITLE: SC-12(4) PKI Certificates
STATEMENT: >>>
Withdrawn. Incorporated into SC-12.3.
<<<
COMMENT: Withdrawn
BASELINE: None
STATUS: Draft

[REQUIREMENT]
UID: SC-12.5
TITLE: SC-12(5) PKI Certificates / Hardware Tokens
STATEMENT: >>>
Withdrawn. Incorporated into SC-12.3.
<<<
COMMENT: Withdrawn
BASELINE: None
STATUS: Draft

[REQUIREMENT]
UID: SC-12.6
TITLE: SC-12(6) Physical Control of Keys
STATEMENT: >>>
Maintain physical control of cryptographic keys when stored information is encrypted by external service providers.
<<<
BASELINE: None
STATUS: Draft

[REQUIREMENT]
UID: SC-13
TITLE: SC-13 Cryptographic Protection
STATEMENT: >>>
a. Determine the [cryptographic uses] ; and

b. Implement the following types of cryptography required for each specified cryptographic use: [types of cryptography].
<<<
COMMENT: Baselines: Low, Moderate, High
BASELINE: Low
STATUS: Draft

[REQUIREMENT]
UID: SC-13.1
TITLE: SC-13(1) FIPS-validated Cryptography
STATEMENT: >>>
Withdrawn. Incorporated into SC-13.
<<<
COMMENT: Withdrawn
BASELINE: None
STATUS: Draft

[REQUIREMENT]
UID: SC-13.2
TITLE: SC-13(2) NSA-approved Cryptography
STATEMENT: >>>
Withdrawn. Incorporated into SC-13.
<<<
COMMENT: Withdrawn
BASELINE: None
STATUS: Draft

[REQUIREMENT]
UID: SC-13.3
TITLE: SC-13(3) Individuals Without Formal Access Approvals
STATEMENT: >>>
Withdrawn. Incorporated into SC-13.
<<<
COMMENT: Withdrawn
BASELINE: None
STATUS: Draft

[REQUIREMENT]
UID: SC-13.4
TITLE: SC-13(4) Digital Signatures
STATEMENT: >>>
Withdrawn. Incorporated into SC-13.
<<<
COMMENT: Withdrawn
BASELINE: None
STATUS: Draft

[REQUIREMENT]
UID: SC-14
TITLE: SC-14 Public Access Protections
STATEMENT: >>>
Withdrawn. Incorporated into AC-2, AC-3, AC-5, AC-6, SI-3, SI-4, SI-5, SI-7, SI-10.
<<<
COMMENT: Withdrawn
BASELINE: None
STATUS: Draft

[REQUIREMENT]
UID: SC-15
TITLE: SC-15 Collaborative Computing Devices and Applications
STATEMENT: >>>
a. Prohibit remote activation of collaborative computing devices and applications with the following exceptions: [exceptions where remote activation is to be allowed] ; and

b. Provide an explicit indication of use to users physically present at the devices.
<<<
COMMENT: Baselines: Low, Moderate, High
BASELINE: Low
STATUS: Draft

[REQUIREMENT]
UID: SC-15.1
TITLE: SC-15(1) Physical or Logical Disconnect
STATEMENT: >>>
Provide [sc-15.01_odp] disconnect of collaborative computing devices in a manner that supports ease of use.
<<<
BASELINE: None
STATUS: Draft

[REQUIREMENT]
UID: SC-15.2
TITLE: SC-15(2) Blocking Inbound and Outbound Communications Traffic
STATEMENT: >>>
Withdrawn. Incorporated into SC-7.
<<<
COMMENT: Withdrawn
BASELINE: None
STATUS: Draft

[REQUIREMENT]
UID: SC-15.3
TITLE: SC-15(3) Disabling and Removal in Secure Work Areas
STATEMENT: >>>
Disable or remove collaborative computing devices and applications from [systems or system components] in [secure work areas].
<<<
BASELINE: None
STATUS: Draft

[REQUIREMENT]
UID: SC-15.4
TITLE: SC-15(4) Explicitly Indicate Current Participants
STATEMENT: >>>
Provide an explicit indication of current participants in [online meetings and teleconferences].
<<<
BASELINE: None
STATUS: Draft

[REQUIREMENT]
UID: SC-16
TITLE: SC-16 Transmission of Security and Privacy Attributes
STATEMENT: >>>
Associate [organization-defined security and privacy attributes] with information exchanged between systems and between system components.
<<<
BASELINE: None
STATUS: Draft

[REQUIREMENT]
UID: SC-16.1
TITLE: SC-16(1) Integrity Verification
STATEMENT: >>>
Verify the integrity of transmitted security and privacy attributes.
<<<
BASELINE: None
STATUS: Draft

[REQUIREMENT]
UID: SC-16.2
TITLE: SC-16(2) Anti-spoofing Mechanisms
STATEMENT: >>>
Implement anti-spoofing mechanisms to prevent adversaries from falsifying the security attributes indicating the successful application of the security process.
<<<
BASELINE: None
STATUS: Draft

[REQUIREMENT]
UID: SC-16.3
TITLE: SC-16(3) Cryptographic Binding
STATEMENT: >>>
Implement [mechanisms or techniques] to bind security and privacy attributes to transmitted information.
<<<
BASELINE: None
STATUS: Draft

[REQUIREMENT]
UID: SC-17
TITLE: SC-17 Public Key Infrastructure Certificates
STATEMENT: >>>
a. Issue public key certificates under an [certificate policy] or obtain public key certificates from an approved service provider; and

b. Include only approved trust anchors in trust stores or certificate stores managed by the organization.
<<<
COMMENT: Baselines: Moderate, High
BASELINE: Moderate
STATUS: Draft

[REQUIREMENT]
UID: SC-18
TITLE: SC-18 Mobile Code
STATEMENT: >>>
a. Define acceptable and unacceptable mobile code and mobile code technologies; and

b. Authorize, monitor, and control the use of mobile code within the system.
<<<
COMMENT: Baselines: Moderate, High
BASELINE: Moderate
STATUS: Draft

[REQUIREMENT]
UID: SC-18.1
TITLE: SC-18(1) Identify Unacceptable Code and Take Corrective Actions
STATEMENT: >>>
Identify [unacceptable mobile code] and take [corrective actions].
<<<
BASELINE: None
STATUS: Draft

[REQUIREMENT]
UID: SC-18.2
TITLE: SC-18(2) Acquisition, Development, and Use
STATEMENT: >>>
Verify that the acquisition, development, and use of mobile code to be deployed in the system meets [mobile code requirements].
<<<
BASELINE: None
STATUS: Draft

[REQUIREMENT]
UID: SC-18.3
TITLE: SC-18(3) Prevent Downloading and Execution
STATEMENT: >>>
Prevent the download and execution of [unacceptable mobile code].
<<<
BASELINE: None
STATUS: Draft

[REQUIREMENT]
UID: SC-18.4
TITLE: SC-18(4) Prevent Automatic Execution
STATEMENT: >>>
Prevent the automatic execution of mobile code in [software applications] and enforce [actions] prior to executing the code.
<<<
BASELINE: None
STATUS: Draft

[REQUIREMENT]
UID: SC-18.5
TITLE: SC-18(5) Allow Execution Only in Confined Environments
STATEMENT: >>>
Allow execution of permitted mobile code only in confined virtual machine environments.
<<<
BASELINE: None
STATUS: Draft

[REQUIREMENT]
UID: SC-19
TITLE: SC-19 Voice Over Internet Protocol
STATEMENT: >>>
Withdrawn.
Technology-specific; addressed as any other technology or protocol.
<<<
COMMENT: Withdrawn
BASELINE: None
STATUS: Draft

[REQUIREMENT]
UID: SC-20
TITLE: SC-20 Secure Name/Address Resolution Service (Authoritative Source)
STATEMENT: >>>
a. Provide additional data origin authentication and integrity verification artifacts along with the authoritative name resolution data the system returns in response to external name/address resolution queries; and

b. Provide the means to indicate the security status of child zones and (if the child supports secure resolution services) to enable verification of a chain of trust among parent and child domains, when operating as part of a distributed, hierarchical namespace.
<<<
COMMENT: Baselines: Low, Moderate, High
BASELINE: Low
STATUS: Draft

[REQUIREMENT]
UID: SC-20.1
TITLE: SC-20(1) Child Subspaces
STATEMENT: >>>
Withdrawn. Incorporated into SC-20.
<<<
COMMENT: Withdrawn
BASELINE: None
STATUS: Draft

[REQUIREMENT]
UID: SC-20.2
TITLE: SC-20(2) Data Origin and Integrity
STATEMENT: >>>
Provide data origin and integrity protection artifacts for internal name/address resolution queries.
<<<
BASELINE: None
STATUS: Draft

[REQUIREMENT]
UID: SC-21
TITLE: SC-21 Secure Name/Address Resolution Service (Recursive or Caching Resolver)
STATEMENT: >>>
Request and perform data origin authentication and data integrity verification on the name/address resolution responses the system receives from authoritative sources.
<<<
COMMENT: Baselines: Low, Moderate, High
BASELINE: Low
STATUS: Draft

[REQUIREMENT]
UID: SC-21.1
TITLE: SC-21(1) Data Origin and Integrity
STATEMENT: >>>
Withdrawn. Incorporated into SC-21.
<<<
COMMENT: Withdrawn
BASELINE: None
STATUS: Draft

[REQUIREMENT]
UID: SC-22
TITLE: SC-22 Architecture and Provisioning for Name/Address Resolution Service
STATEMENT: >>>
Ensure the systems that collectively provide name/address resolution service for an organization are fault-tolerant and implement internal and external role separation.
<<<
COMMENT: Baselines: Low, Moderate, High
BASELINE: Low
STATUS: Draft

[REQUIREMENT]
UID: SC-23
TITLE: SC-23 Session Authenticity
STATEMENT: >>>
Protect the authenticity of communications sessions.
<<<
COMMENT: Baselines: Moderate, High
BASELINE: Moderate
STATUS: Draft

[REQUIREMENT]
UID: SC-23.1
TITLE: SC-23(1) Invalidate Session Identifiers at Logout
STATEMENT: >>>
Invalidate session identifiers upon user logout or other session termination.
<<<
BASELINE: None
STATUS: Draft

[REQUIREMENT]
UID: SC-23.2
TITLE: SC-23(2) User-initiated Logouts and Message Displays
STATEMENT: >>>
Withdrawn. Incorporated into AC-12.1.
<<<
COMMENT: Withdrawn
BASELINE: None
STATUS: Draft

[REQUIREMENT]
UID: SC-23.3
TITLE: SC-23(3) Unique System-generated Session Identifiers
STATEMENT: >>>
Generate a unique session identifier for each session with [randomness requirements] and recognize only session identifiers that are system-generated.
<<<
BASELINE: None
STATUS: Draft

[REQUIREMENT]
UID: SC-23.4
TITLE: SC-23(4) Unique Session Identifiers with Randomization
STATEMENT: >>>
Withdrawn. Incorporated into SC-23.3.
<<<
COMMENT: Withdrawn
BASELINE: None
STATUS: Draft

[REQUIREMENT]
UID: SC-23.5
TITLE: SC-23(5) Allowed Certificate Authorities
STATEMENT: >>>
Only allow the use of [certificated authorities] for verification of the establishment of protected sessions.
<<<
BASELINE: None
STATUS: Draft

[REQUIREMENT]
UID: SC-24
TITLE: SC-24 Fail in Known State
STATEMENT: >>>
Fail to a [known system state] for the following failures on the indicated components while preserving [system state information] in failure: [types of system failures on system components].
<<<
COMMENT: Baselines: High
BASELINE: High
STATUS: Draft

[REQUIREMENT]
UID: SC-25
TITLE: SC-25 Thin Nodes
STATEMENT: >>>
Employ minimal functionality and information storage on the following system components: [system components].
<<<
BASELINE: None
STATUS: Draft

[REQUIREMENT]
UID: SC-26
TITLE: SC-26 Decoys
STATEMENT: >>>
Include components within organizational systems specifically designed to be the target of malicious attacks for detecting, deflecting, and analyzing such attacks.
<<<
BASELINE: None
STATUS: Draft

[REQUIREMENT]
UID: SC-26.1
TITLE: SC-26(1) Detection of Malicious Code
STATEMENT: >>>
Withdrawn. Incorporated into SC-35.
<<<
COMMENT: Withdrawn
BASELINE: None
STATUS: Draft

[REQUIREMENT]
UID: SC-27
TITLE: SC-27 Platform-independent Applications
STATEMENT: >>>
Include within organizational systems the following platform independent applications: [platform-independent applications].
<<<
BASELINE: None
STATUS: Draft

[REQUIREMENT]
UID: SC-28
TITLE: SC-28 Protection of Information at Rest
STATEMENT: >>>
Protect the [sc-28_odp.01] of the following information at rest: [information at rest].
<<<
COMMENT: Baselines: Moderate, High
BASELINE: Moderate
STATUS: Draft

[REQUIREMENT]
UID: SC-28.1
TITLE: SC-28(1) Cryptographic Protection
STATEMENT: >>>
Implement cryptographic mechanisms to prevent unauthorized disclosure and modification of the following information at rest on [system components or media]: [information].
<<<
COMMENT: Baselines: Moderate, High
BASELINE: Moderate
STATUS: Draft

[REQUIREMENT]
UID: SC-28.2
TITLE: SC-28(2) Offline Storage
STATEMENT: >>>
Remove the following information from online storage and store offline in a secure location: [information].
<<<
BASELINE: None
STATUS: Draft

[REQUIREMENT]
UID: SC-28.3
TITLE: SC-28(3) Cryptographic Keys
STATEMENT: >>>
Provide protected storage for cryptographic keys [sc-28.03_odp.01].
<<<
BASELINE: None
STATUS: Draft

[REQUIREMENT]
UID: SC-29
TITLE: SC-29 Heterogeneity
STATEMENT: >>>
Employ a diverse set of information technologies for the following system components in the implementation of the system: [system components].
<<<
BASELINE: None
STATUS: Draft

[REQUIREMENT]
UID: SC-29.1
TITLE: SC-29(1) Virtualization Techniques
STATEMENT: >>>
Employ virtualization techniques to support the deployment of a diversity of operating systems and applications that are changed [frequency].
<<<
BASELINE: None
STATUS: Draft

[REQUIREMENT]
UID: SC-30
TITLE: SC-30 Concealment and Misdirection
STATEMENT: >>>
Employ the following concealment and misdirection techniques for [systems] at [time periods] to confuse and mislead adversaries: [concealment and misdirection techniques].
<<<
BASELINE: None
STATUS: Draft

[REQUIREMENT]
UID: SC-30.1
TITLE: SC-30(1) Virtualization Techniques
STATEMENT: >>>
Withdrawn. Incorporated into SC-29.1.
<<<
COMMENT: Withdrawn
BASELINE: None
STATUS: Draft

[REQUIREMENT]
UID: SC-30.2
TITLE: SC-30(2) Randomness
STATEMENT: >>>
Employ [techniques] to introduce randomness into organizational operations and assets.
<<<
BASELINE: None
STATUS: Draft

[REQUIREMENT]
UID: SC-30.3
TITLE: SC-30(3) Change Processing and Storage Locations
STATEMENT: >>>
Change the location of [processing and/or storage] [sc-30.03_odp.02]].
<<<
BASELINE: None
STATUS: Draft

[REQUIREMENT]
UID: SC-30.4
TITLE: SC-30(4) Misleading Information
STATEMENT: >>>
Employ realistic, but misleading information in [system components] about its security state or posture.
<<<
BASELINE: None
STATUS: Draft

[REQUIREMENT]
UID: SC-30.5
TITLE: SC-30(5) Concealment of System Components
STATEMENT: >>>
Employ the following techniques to hide or conceal [system components]: [techniques].
<<<
BASELINE: None
STATUS: Draft

[REQUIREMENT]
UID: SC-31
TITLE: SC-31 Covert Channel Analysis
STATEMENT: >>>
a. Perform a covert channel analysis to identify those aspects of communications within the system that are potential avenues for covert [sc-31_odp] channels; and

b. Estimate the maximum bandwidth of those channels.
<<<
BASELINE: None
STATUS: Draft

[REQUIREMENT]
UID: SC-31.1
TITLE: SC-31(1) Test Covert Channels for Exploitability
STATEMENT: >>>
Test a subset of the identified covert channels to determine the channels that are exploitable.
<<<
BASELINE: None
STATUS: Draft

[REQUIREMENT]
UID: SC-31.2
TITLE: SC-31(2) Maximum Bandwidth
STATEMENT: >>>
Reduce the maximum bandwidth for identified covert [sc-31.02_odp.01] channels to [values].
<<<
BASELINE: None
STATUS: Draft

[REQUIREMENT]
UID: SC-31.3
TITLE: SC-31(3) Measure Bandwidth in Operational Environments
STATEMENT: >>>
Measure the bandwidth of [subset of identified covert channels] in the operational environment of the system.
<<<
BASELINE: None
STATUS: Draft

[REQUIREMENT]
UID: SC-32
TITLE: SC-32 System Partitioning
STATEMENT: >>>
Partition the system into [system components] residing in separate [sc-32_odp.02] domains or environments based on [circumstances for the physical or logical separation of components].
<<<
BASELINE: None
STATUS: Draft

[REQUIREMENT]
UID: SC-32.1
TITLE: SC-32(1) Separate Physical Domains for Privileged Functions
STATEMENT: >>>
Partition privileged functions into separate physical domains.
<<<
BASELINE: None
STATUS: Draft

[REQUIREMENT]
UID: SC-33
TITLE: SC-33 Transmission Preparation Integrity
STATEMENT: >>>
Withdrawn. Incorporated into SC-8.
<<<
COMMENT: Withdrawn
BASELINE: None
STATUS: Draft

[REQUIREMENT]
UID: SC-34
TITLE: SC-34 Non-modifiable Executable Programs
STATEMENT: >>>
For [system components] , load and execute:

  a. The operating environment from hardware-enforced, read-only media; and

  b. The following applications from hardware-enforced, read-only media: [applications].
<<<
BASELINE: None
STATUS: Draft

[REQUIREMENT]
UID: SC-34.1
TITLE: SC-34(1) No Writable Storage
STATEMENT: >>>
Employ [system components] with no writeable storage that is persistent across component restart or power on/off.
<<<
BASELINE: None
STATUS: Draft

[REQUIREMENT]
UID: SC-34.2
TITLE: SC-34(2) Integrity Protection on Read-only Media
STATEMENT: >>>
Protect the integrity of information prior to storage on read-only media and control the media after such information has been recorded onto the media.
<<<
BASELINE: None
STATUS: Draft

[REQUIREMENT]
UID: SC-34.3
TITLE: SC-34(3) Hardware-based Protection
STATEMENT: >>>
Withdrawn.
<<<
COMMENT: Withdrawn
BASELINE: None
STATUS: Draft

[REQUIREMENT]
UID: SC-35
TITLE: SC-35 External Malicious Code Identification
STATEMENT: >>>
Include system components that proactively seek to identify network-based malicious code or malicious websites.
<<<
BASELINE: None
STATUS: Draft

[REQUIREMENT]
UID: SC-36
TITLE: SC-36 Distributed Processing and Storage
STATEMENT: >>>
Distribute the following processing and storage components across multiple [sc-36_prm_1]: [organization-defined processing and storage components].
<<<
BASELINE: None
STATUS: Draft

[REQUIREMENT]
UID: SC-36.1
TITLE: SC-36(1) Polling Techniques
STATEMENT: >>>
(a) Employ polling techniques to identify potential faults, errors, or compromises to the following processing and storage components: [distributed processing and storage components] ; and

(b) Take the following actions in response to identified faults, errors, or compromises: [actions].
<<<
BASELINE: None
STATUS: Draft

[REQUIREMENT]
UID: SC-36.2
TITLE: SC-36(2) Synchronization
STATEMENT: >>>
Synchronize the following duplicate systems or system components: [duplicate systems or system components].
<<<
BASELINE: None
STATUS: Draft

[REQUIREMENT]
UID: SC-37
TITLE: SC-37 Out-of-band Channels
STATEMENT: >>>
Employ the following out-of-band channels for the physical delivery or electronic transmission of [information, system components, or devices] to [individuals or systems]: [out-of-band channels].
<<<
BASELINE: None
STATUS: Draft

[REQUIREMENT]
UID: SC-37.1
TITLE: SC-37(1) Ensure Delivery and Transmission
STATEMENT: >>>
Employ [controls] to ensure that only [individuals or systems] receive the following information, system components, or devices: [information, system components, or devices].
<<<
BASELINE: None
STATUS: Draft

[REQUIREMENT]
UID: SC-38
TITLE: SC-38 Operations Security
STATEMENT: >>>
Employ the following operations security controls to protect key organizational information throughout the system development life cycle: [operations security controls].
<<<
BASELINE: None
STATUS: Draft

[REQUIREMENT]
UID: SC-39
TITLE: SC-39 Process Isolation
STATEMENT: >>>
Maintain a separate execution domain for each executing system process.
<<<
COMMENT: Baselines: Low, Moderate, High
BASELINE: Low
STATUS: Draft

[REQUIREMENT]
UID: SC-39.1
TITLE: SC-39(1) Hardware Separation
STATEMENT: >>>
Implement hardware separation mechanisms to facilitate process isolation.
<<<
BASELINE: None
STATUS: Draft

[REQUIREMENT]
UID: SC-39.2
TITLE: SC-39(2) Separate Execution Domain Per Thread
STATEMENT: >>>
Maintain a separate execution domain for each thread in [multi-threaded processing].
<<<
BASELINE: None
STATUS: Draft

[REQUIREMENT]
UID: SC-40
TITLE: SC-40 Wireless Link Protection
STATEMENT: >>>
Protect external and internal [organization-defined wireless links] from the following signal parameter attacks: [organization-defined types of signal parameter attacks or references to sources for such attacks].
<<<
BASELINE: None
STATUS: Draft

[REQUIREMENT]
UID: SC-40.1
TITLE: SC-40(1) Electromagnetic Interference
STATEMENT: >>>
Implement cryptographic mechanisms that achieve [level of protection] against the effects of intentional electromagnetic interference.
<<<
BASELINE: None
STATUS: Draft

[REQUIREMENT]
UID: SC-40.2
TITLE: SC-40(2) Reduce Detection Potential
STATEMENT: >>>
Implement cryptographic mechanisms to reduce the detection potential of wireless links to [level of reduction].
<<<
BASELINE: None
STATUS: Draft

[REQUIREMENT]
UID: SC-40.3
TITLE: SC-40(3) Imitative or Manipulative Communications Deception
STATEMENT: >>>
Implement cryptographic mechanisms to identify and reject wireless transmissions that are deliberate attempts to achieve imitative or manipulative communications deception based on signal parameters.
<<<
BASELINE: None
STATUS: Draft

[REQUIREMENT]
UID: SC-40.4
TITLE: SC-40(4) Signal Parameter Identification
STATEMENT: >>>
Implement cryptographic mechanisms to prevent the identification of [wireless transmitters] by using the transmitter signal parameters.
<<<
BASELINE: None
STATUS: Draft

[REQUIREMENT]
UID: SC-41
TITLE: SC-41 Port and I/O Device Access
STATEMENT: >>>
[sc-41_odp.02] disable or remove [connection ports or input/output devices] on the following systems or system components: [systems or system components].
<<<
BASELINE: None
STATUS: Draft

[REQUIREMENT]
UID: SC-42
TITLE: SC-42 Sensor Capability and Data
STATEMENT: >>>
a. Prohibit [sc-42_odp.01] ; and

b. Provide an explicit indication of sensor use to [group of users].
<<<
BASELINE: None
STATUS: Draft

[REQUIREMENT]
UID: SC-42.1
TITLE: SC-42(1) Reporting to Authorized Individuals or Roles
STATEMENT: >>>
Verify that the system is configured so that data or information collected by the [sensors] is only reported to authorized individuals or roles.
<<<
BASELINE: None
STATUS: Draft

[REQUIREMENT]
UID: SC-42.2
TITLE: SC-42(2) Authorized Use
STATEMENT: >>>
Employ the following measures so that data or information collected by [sc-42.01_odp] is only used for authorized purposes: [measures].
<<<
BASELINE: None
STATUS: Draft

[REQUIREMENT]
UID: SC-42.3
TITLE: SC-42(3) Prohibit Use of Devices
STATEMENT: >>>
Withdrawn. Incorporated into SC-42.
<<<
COMMENT: Withdrawn
BASELINE: None
STATUS: Draft

[REQUIREMENT]
UID: SC-42.4
TITLE: SC-42(4) Notice of Collection
STATEMENT: >>>
Employ the following measures to facilitate an individual’s awareness that personally identifiable information is being collected by [sensors]: [measures].
<<<
BASELINE: None
STATUS: Draft

[REQUIREMENT]
UID: SC-42.5
TITLE: SC-42(5) Collection Minimization
STATEMENT: >>>
Employ [sensors] that are configured to minimize the collection of information about individuals that is not needed.
<<<
BASELINE: None
STATUS: Draft

[REQUIREMENT]
UID: SC-43
TITLE: SC-43 Usage Restrictions
STATEMENT: >>>
a. Establish usage restrictions and implementation guidelines for the following system components: [components] ; and

b. Authorize, monitor, and control the use of such components within the system.
<<<
BASELINE: None
STATUS: Draft

[REQUIREMENT]
UID: SC-44
TITLE: SC-44 Detonation Chambers
STATEMENT: >>>
Employ a detonation chamber capability within [system, system component, or location].
<<<
BASELINE: None
STATUS: Draft

[REQUIREMENT]
UID: SC-45
TITLE: SC-45 System Time Synchronization
STATEMENT: >>>
Synchronize system clocks within and between systems and system components.
<<<
BASELINE: None
STATUS: Draft

[REQUIREMENT]
UID: SC-45.1
TITLE: SC-45(1) Synchronization with Authoritative Time Source
STATEMENT: >>>
(a) Compare the internal system clocks [frequency] with [authoritative time source] ; and

(b) Synchronize the internal system clocks to the authoritative time source when the time difference is greater than [time period].
<<<
BASELINE: None
STATUS: Draft

[REQUIREMENT]
UID: SC-45.2
TITLE: SC-45(2) Secondary Authoritative Time Source
STATEMENT: >>>
(a) Identify a secondary authoritative time source that is in a different geographic region than the primary authoritative time source; and

(b) Synchronize the internal system clocks to the secondary authoritative time source if the primary authoritative time source is unavailable.
<<<
BASELINE: None
STATUS: Draft

[REQUIREMENT]
UID: SC-46
TITLE: SC-46 Cross Domain Policy Enforcement
STATEMENT: >>>
Implement a policy enforcement mechanism [sc-46_odp] between the physical and/or network interfaces for the connecting security domains.
<<<
BASELINE: None
STATUS: Draft

[REQUIREMENT]
UID: SC-47
TITLE: SC-47 Alternate Communications Paths
STATEMENT: >>>
Establish [alternate communication paths] for system operations organizational command and control.
<<<
BASELINE: None
STATUS: Draft

[REQUIREMENT]
UID: SC-48
TITLE: SC-48 Sensor Relocation
STATEMENT: >>>
Relocate [sensors and monitoring capabilities] to [locations] under the following conditions or circumstances: [conditions or circumstances].
<<<
BASELINE: None
STATUS: Draft

[REQUIREMENT]
UID: SC-48.1
TITLE: SC-48(1) Dynamic Relocation of Sensors or Monitoring Capabilities
STATEMENT: >>>
Dynamically relocate [sensors and monitoring capabilities] to [locations] under the following conditions or circumstances: [conditions or circumstances].
<<<
BASELINE: None
STATUS: Draft

[REQUIREMENT]
UID: SC-49
TITLE: SC-49 Hardware-enforced Separation and Policy Enforcement
STATEMENT: >>>
Implement hardware-enforced separation and policy enforcement mechanisms between [security domains].
<<<
BASELINE: None
STATUS: Draft

[REQUIREMENT]
UID: SC-50
TITLE: SC-50 Software-enforced Separation and Policy Enforcement
STATEMENT: >>>
Implement software-enforced separation and policy enforcement mechanisms between [security domains].
<<<
BASELINE: None
STATUS: Draft

[REQUIREMENT]
UID: SC-51
TITLE: SC-51 Hardware-based Protection
STATEMENT: >>>
a. Employ hardware-based, write-protect for [system firmware components] ; and

b. Implement specific procedures for [authorized individuals] to manually disable hardware write-protect for firmware modifications and re-enable the write-protect prior to returning to operational mode.
<<<
BASELINE: None
STATUS: Draft

[[/SECTION]]

[[SECTION]]
UID: NIST-SI
TITLE: SI — System and Information Integrity

[REQUIREMENT]
UID: SI-1
TITLE: SI-1 Policy and Procedures
STATEMENT: >>>
a. Develop, document, and disseminate to [organization-defined personnel or roles]:

  1. [si-01_odp.03] system and information integrity policy that:

    (a) Addresses purpose, scope, roles, responsibilities, management commitment, coordination among organizational entities, and compliance; and

    (b) Is consistent with applicable laws, executive orders, directives, regulations, policies, standards, and guidelines; and

  2. Procedures to facilitate the implementation of the system and information integrity policy and the associated system and information integrity controls;

b. Designate an [official] to manage the development, documentation, and dissemination of the system and information integrity policy and procedures; and

c. Review and update the current system and information integrity:

  1. Policy [frequency] and following [events] ; and

  2. Procedures [frequency] and following [events].
<<<
COMMENT: Baselines: Low, Moderate, High, Privacy
BASELINE: Low
STATUS: Draft

[REQUIREMENT]
UID: SI-2
TITLE: SI-2 Flaw Remediation
STATEMENT: >>>
a. Identify, report, and correct system flaws;

b. Test software and firmware updates related to flaw remediation for effectiveness and potential side effects before installation;

c. Install security-relevant software and firmware updates within [time period] of the release of the updates; and

d. Incorporate flaw remediation into the organizational configuration management process.
<<<
COMMENT: Baselines: Low, Moderate, High
BASELINE: Low
STATUS: Draft

[REQUIREMENT]
UID: SI-2.1
TITLE: SI-2(1) Central Management
STATEMENT: >>>
Withdrawn. Incorporated into PL-9.
<<<
COMMENT: Withdrawn
BASELINE: None
STATUS: Draft

[REQUIREMENT]
UID: SI-2.2
TITLE: SI-2(2) Automated Flaw Remediation Status
STATEMENT: >>>
Determine if system components have applicable security-relevant software and firmware updates installed using [automated mechanisms] [frequency].
<<<
COMMENT: Baselines: Moderate, High
BASELINE: Moderate
STATUS: Draft

[REQUIREMENT]
UID: SI-2.3
TITLE: SI-2(3) Time to Remediate Flaws and Benchmarks for Corrective Actions
STATEMENT: >>>
(a) Measure the time between flaw identification and flaw remediation; and

(b) Establish the following benchmarks for taking corrective actions: [benchmarks].
<<<
BASELINE: None
STATUS: Draft

[REQUIREMENT]
UID: SI-2.4
TITLE: SI-2(4) Automated Patch Management Tools
STATEMENT: >>>
Employ automated patch management tools to facilitate flaw remediation to the following system components: [components].
<<<
BASELINE: None
STATUS: Draft

[REQUIREMENT]
UID: SI-2.5
TITLE: SI-2(5) Automatic Software and Firmware Updates
STATEMENT: >>>
Install [security-relevant software and firmware updates] automatically to [system components].
<<<
BASELINE: None
STATUS: Draft

[REQUIREMENT]
UID: SI-2.6
TITLE: SI-2(6) Removal of Previous Versions of Software and Firmware
STATEMENT: >>>
Remove previous versions of [software and firmware components] after updated versions have been installed.
<<<
BASELINE: None
STATUS: Draft

[REQUIREMENT]
UID: SI-2.7
TITLE: SI-2(7) Root Cause Analysis
STATEMENT: >>>
a. Conduct root cause analysis to identify underlying causes of issues or failures.

b. Develop actions to address the root cause of the issue or failure.

c. Implement the actions and monitor the implementation for effectiveness.
<<<
BASELINE: None
STATUS: Draft

[REQUIREMENT]
UID: SI-3
TITLE: SI-3 Malicious Code Protection
STATEMENT: >>>
a. Implement [si-03_odp.01] malicious code protection mechanisms at system entry and exit points to detect and eradicate malicious code;

b. Automatically update malicious code protection mechanisms as new releases are available in accordance with organizational configuration management policy and procedures;

c. Configure malicious code protection mechanisms to:

  1. Perform periodic scans of the system [frequency] and real-time scans of files from external sources at [si-03_odp.03] as the files are downloaded, opened, or executed in accordance with organizational policy; and

  2. [si-03_odp.04] ; and send alert to [personnel or roles] in response to malicious code detection; and

d. Address the receipt of false positives during malicious code detection and eradication and the resulting potential impact on the availability of the system.
<<<
COMMENT: Baselines: Low, Moderate, High
BASELINE: Low
STATUS: Draft

[REQUIREMENT]
UID: SI-3.1
TITLE: SI-3(1) Central Management
STATEMENT: >>>
Withdrawn. Incorporated into PL-9.
<<<
COMMENT: Withdrawn
BASELINE: None
STATUS: Draft

[REQUIREMENT]
UID: SI-3.2
TITLE: SI-3(2) Automatic Updates
STATEMENT: >>>
Withdrawn. Incorporated into SI-3.
<<<
COMMENT: Withdrawn
BASELINE: None
STATUS: Draft

[REQUIREMENT]
UID: SI-3.3
TITLE: SI-3(3) Non-privileged Users
STATEMENT: >>>
Withdrawn. Incorporated into AC-6.10.
<<<
COMMENT: Withdrawn
BASELINE: None
STATUS: Draft

[REQUIREMENT]
UID: SI-3.4
TITLE: SI-3(4) Updates Only by Privileged Users
STATEMENT: >>>
Update malicious code protection mechanisms only when directed by a privileged user.
<<<
BASELINE: None
STATUS: Draft

[REQUIREMENT]
UID: SI-3.5
TITLE: SI-3(5) Portable Storage Devices
STATEMENT: >>>
Withdrawn. Incorporated into MP-7.
<<<
COMMENT: Withdrawn
BASELINE: None
STATUS: Draft

[REQUIREMENT]
UID: SI-3.6
TITLE: SI-3(6) Testing and Verification
STATEMENT: >>>
(a) Test malicious code protection mechanisms [frequency] by introducing known benign code into the system; and

(b) Verify that the detection of the code and the associated incident reporting occur.
<<<
BASELINE: None
STATUS: Draft

[REQUIREMENT]
UID: SI-3.7
TITLE: SI-3(7) Nonsignature-based Detection
STATEMENT: >>>
Withdrawn. Incorporated into SI-3.
<<<
COMMENT: Withdrawn
BASELINE: None
STATUS: Draft

[REQUIREMENT]
UID: SI-3.8
TITLE: SI-3(8) Detect Unauthorized Commands
STATEMENT: >>>
(a) Detect the following unauthorized operating system commands through the kernel application programming interface on [system hardware components]: [unauthorized operating system commands] ; and

(b) [si-03.08_odp.03].
<<<
BASELINE: None
STATUS: Draft

[REQUIREMENT]
UID: SI-3.9
TITLE: SI-3(9) Authenticate Remote Commands
STATEMENT: >>>
Withdrawn.
<<<
COMMENT: Withdrawn
BASELINE: None
STATUS: Draft

[REQUIREMENT]
UID: SI-3.10
TITLE: SI-3(10) Malicious Code Analysis
STATEMENT: >>>
(a) Employ the following tools and techniques to analyze the characteristics and behavior of malicious code: [tools and techniques] ; and

(b) Incorporate the results from malicious code analysis into organizational incident response and flaw remediation processes.
<<<
BASELINE: None
STATUS: Draft

[REQUIREMENT]
UID: SI-4
TITLE: SI-4 System Monitoring
STATEMENT: >>>
a. Monitor the system to detect:

  1. Attacks and indicators of potential attacks in accordance with the following monitoring objectives: [monitoring objectives] ; and

  2. Unauthorized local, network, and remote connections;

b. Identify unauthorized use of the system through the following techniques and methods: [techniques and methods];

c. Invoke internal monitoring capabilities or deploy monitoring devices:

  1. Strategically within the system to collect organization-determined essential information; and

  2. At ad hoc locations within the system to track specific types of transactions of interest to the organization;

d. Analyze detected events and anomalies;

e. Adjust the level of system monitoring activity when there is a change in risk to organizational operations and assets, individuals, other organizations, or the Nation;

f. Obtain legal opinion regarding system monitoring activities; and

g. Provide [system monitoring information] to [personnel or roles] [si-04_odp.05].
<<<
COMMENT: Baselines: Low, Moderate, High
BASELINE: Low
STATUS: Draft

[REQUIREMENT]
UID: SI-4.1
TITLE: SI-4(1) System-wide Intrusion Detection System
STATEMENT: >>>
Connect and configure individual intrusion detection tools into a system-wide intrusion detection system.
<<<
BASELINE: None
STATUS: Draft

[REQUIREMENT]
UID: SI-4.2
TITLE: SI-4(2) Automated Tools and Mechanisms for Real-time Analysis
STATEMENT: >>>
Employ automated tools and mechanisms to support near real-time analysis of events.
<<<
COMMENT: Baselines: Moderate, High
BASELINE: Moderate
STATUS: Draft

[REQUIREMENT]
UID: SI-4.3
TITLE: SI-4(3) Automated Tool and Mechanism Integration
STATEMENT: >>>
Employ automated tools and mechanisms to integrate intrusion detection tools and mechanisms into access control and flow control mechanisms.
<<<
BASELINE: None
STATUS: Draft

[REQUIREMENT]
UID: SI-4.4
TITLE: SI-4(4) Inbound and Outbound Communications Traffic
STATEMENT: >>>
(a) Determine criteria for unusual or unauthorized activities or conditions for inbound and outbound communications traffic;

(b) Monitor inbound and outbound communications traffic [organization-defined frequency] for [organization-defined unusual or unauthorized activities or conditions].
<<<
COMMENT: Baselines: Moderate, High
BASELINE: Moderate
STATUS: Draft

[REQUIREMENT]
UID: SI-4.5
TITLE: SI-4(5) System-generated Alerts
STATEMENT: >>>
Alert [personnel or roles] when the following system-generated indications of compromise or potential compromise occur: [compromise indicators].
<<<
COMMENT: Baselines: Moderate, High
BASELINE: Moderate
STATUS: Draft

[REQUIREMENT]
UID: SI-4.6
TITLE: SI-4(6) Restrict Non-privileged Users
STATEMENT: >>>
Withdrawn. Incorporated into AC-6.10.
<<<
COMMENT: Withdrawn
BASELINE: None
STATUS: Draft

[REQUIREMENT]
UID: SI-4.7
TITLE: SI-4(7) Automated Response to Suspicious Events
STATEMENT: >>>
(a) Notify [incident response personnel] of detected suspicious events; and

(b) Take the following actions upon detection: [least-disruptive actions].
<<<
BASELINE: None
STATUS: Draft

[REQUIREMENT]
UID: SI-4.8
TITLE: SI-4(8) Protection of Monitoring Information
STATEMENT: >>>
Withdrawn. Incorporated into SI-4.
<<<
COMMENT: Withdrawn
BASELINE: None
STATUS: Draft

[REQUIREMENT]
UID: SI-4.9
TITLE: SI-4(9) Testing of Monitoring Tools and Mechanisms
STATEMENT: >>>
Test intrusion-monitoring tools and mechanisms [frequency].
<<<
BASELINE: None
STATUS: Draft

[REQUIREMENT]
UID: SI-4.10
TITLE: SI-4(10) Visibility of Encrypted Communications
STATEMENT: >>>
Make provisions so that [encrypted communications traffic] is visible to [system monitoring tools and mechanisms].
<<<
COMMENT: Baselines: High
BASELINE: High
STATUS: Draft

[REQUIREMENT]
UID: SI-4.11
TITLE: SI-4(11) Analyze Communications Traffic Anomalies
STATEMENT: >>>
Analyze outbound communications traffic at the external interfaces to the system and selected [interior points] to discover anomalies.
<<<
BASELINE: None
STATUS: Draft

[REQUIREMENT]
UID: SI-4.12
TITLE: SI-4(12) Automated Organization-generated Alerts
STATEMENT: >>>
Alert [personnel or roles] using [automated mechanisms] when the following indications of inappropriate or unusual activities with security or privacy implications occur: [activities that trigger alerts].
<<<
COMMENT: Baselines: High
BASELINE: High
STATUS: Draft

[REQUIREMENT]
UID: SI-4.13
TITLE: SI-4(13) Analyze Traffic and Event Patterns
STATEMENT: >>>
(a) Analyze communications traffic and event patterns for the system;

(b) Develop profiles representing common traffic and event patterns; and

(c) Use the traffic and event profiles in tuning system-monitoring devices.
<<<
BASELINE: None
STATUS: Draft

[REQUIREMENT]
UID: SI-4.14
TITLE: SI-4(14) Wireless Intrusion Detection
STATEMENT: >>>
Employ a wireless intrusion detection system to identify rogue wireless devices and to detect attack attempts and potential compromises or breaches to the system.
<<<
COMMENT: Baselines: High
BASELINE: High
STATUS: Draft

[REQUIREMENT]
UID: SI-4.15
TITLE: SI-4(15) Wireless to Wireline Communications
STATEMENT: >>>
Employ an intrusion detection system to monitor wireless communications traffic as the traffic passes from wireless to wireline networks.
<<<
BASELINE: None
STATUS: Draft

[REQUIREMENT]
UID: SI-4.16
TITLE: SI-4(16) Correlate Monitoring Information
STATEMENT: >>>
Correlate information from monitoring tools and mechanisms employed throughout the system.
<<<
BASELINE: None
STATUS: Draft

[REQUIREMENT]
UID: SI-4.17
TITLE: SI-4(17) Integrated Situational Awareness
STATEMENT: >>>
Correlate information from monitoring physical, cyber, and supply chain activities to achieve integrated, organization-wide situational awareness.
<<<
BASELINE: None
STATUS: Draft

[REQUIREMENT]
UID: SI-4.18
TITLE: SI-4(18) Analyze Traffic and Covert Exfiltration
STATEMENT: >>>
Analyze outbound communications traffic at external interfaces to the system and at the following interior points to detect covert exfiltration of information: [interior points].
<<<
BASELINE: None
STATUS: Draft

[REQUIREMENT]
UID: SI-4.19
TITLE: SI-4(19) Risk for Individuals
STATEMENT: >>>
Implement [additional monitoring] of individuals who have been identified by [sources] as posing an increased level of risk.
<<<
BASELINE: None
STATUS: Draft

[REQUIREMENT]
UID: SI-4.20
TITLE: SI-4(20) Privileged Users
STATEMENT: >>>
Implement the following additional monitoring of privileged users: [additional monitoring].
<<<
COMMENT: Baselines: High
BASELINE: High
STATUS: Draft

[REQUIREMENT]
UID: SI-4.21
TITLE: SI-4(21) Probationary Periods
STATEMENT: >>>
Implement the following additional monitoring of individuals during [probationary period]: [additional monitoring].
<<<
BASELINE: None
STATUS: Draft

[REQUIREMENT]
UID: SI-4.22
TITLE: SI-4(22) Unauthorized Network Services
STATEMENT: >>>
(a) Detect network services that have not been authorized or approved by [authorization or approval processes] ; and

(b) [si-04.22_odp.02] when detected.
<<<
COMMENT: Baselines: High
BASELINE: High
STATUS: Draft

[REQUIREMENT]
UID: SI-4.23
TITLE: SI-4(23) Host-based Devices
STATEMENT: >>>
Implement the following host-based monitoring mechanisms at [system components]: [host-based monitoring mechanisms].
<<<
BASELINE: None
STATUS: Draft

[REQUIREMENT]
UID: SI-4.24
TITLE: SI-4(24) Indicators of Compromise
STATEMENT: >>>
Discover, collect, and distribute to [personnel or roles] , indicators of compromise provided by [sources].
<<<
BASELINE: None
STATUS: Draft

[REQUIREMENT]
UID: SI-4.25
TITLE: SI-4(25) Optimize Network Traffic Analysis
STATEMENT: >>>
Provide visibility into network traffic at external and key internal system interfaces to optimize the effectiveness of monitoring devices.
<<<
BASELINE: None
STATUS: Draft

[REQUIREMENT]
UID: SI-5
TITLE: SI-5 Security Alerts, Advisories, and Directives
STATEMENT: >>>
a. Receive system security alerts, advisories, and directives from [external organizations] on an ongoing basis;

b. Generate internal security alerts, advisories, and directives as deemed necessary;

c. Disseminate security alerts, advisories, and directives to: [si-05_odp.02] ; and

d. Implement security directives in accordance with established time frames, or notify the issuing organization of the degree of noncompliance.
<<<
COMMENT: Baselines: Low, Moderate, High
BASELINE: Low
STATUS: Draft

[REQUIREMENT]
UID: SI-5.1
TITLE: SI-5(1) Automated Alerts and Advisories
STATEMENT: >>>
Broadcast security alert and advisory information throughout the organization using [automated mechanisms].
<<<
COMMENT: Baselines: High
BASELINE: High
STATUS: Draft

[REQUIREMENT]
UID: SI-6
TITLE: SI-6 Security and Privacy Function Verification
STATEMENT: >>>
a. Verify the correct operation of [organization-defined security and privacy functions];

b. Perform the verification of the functions specified in SI-6a [si-06_odp.03];

c. Alert [personnel or roles] to failed security and privacy verification tests; and

d. [si-06_odp.07] when anomalies are discovered.
<<<
COMMENT: Baselines: High
BASELINE: High
STATUS: Draft

[REQUIREMENT]
UID: SI-6.1
TITLE: SI-6(1) Notification of Failed Security Tests
STATEMENT: >>>
Withdrawn. Incorporated into SI-6.
<<<
COMMENT: Withdrawn
BASELINE: None
STATUS: Draft

[REQUIREMENT]
UID: SI-6.2
TITLE: SI-6(2) Automation Support for Distributed Testing
STATEMENT: >>>
Implement automated mechanisms to support the management of distributed security and privacy function testing.
<<<
BASELINE: None
STATUS: Draft

[REQUIREMENT]
UID: SI-6.3
TITLE: SI-6(3) Report Verification Results
STATEMENT: >>>
Report the results of security and privacy function verification to [personnel or roles].
<<<
BASELINE: None
STATUS: Draft

[REQUIREMENT]
UID: SI-7
TITLE: SI-7 Software, Firmware, and Information Integrity
STATEMENT: >>>
a. Employ integrity verification tools to detect unauthorized changes to the following software, firmware, and information: [organization-defined software, firmware, and information] ; and

b. Take the following actions when unauthorized changes to the software, firmware, and information are detected: [organization-defined actions].
<<<
COMMENT: Baselines: Moderate, High
BASELINE: Moderate
STATUS: Draft

[REQUIREMENT]
UID: SI-7.1
TITLE: SI-7(1) Integrity Checks
STATEMENT: >>>
Perform an integrity check of [organization-defined software, firmware, and information] [si-7.1_prm_2].
<<<
COMMENT: Baselines: Moderate, High
BASELINE: Moderate
STATUS: Draft

[REQUIREMENT]
UID: SI-7.2
TITLE: SI-7(2) Automated Notifications of Integrity Violations
STATEMENT: >>>
Employ automated tools that provide notification to [personnel or roles] upon discovering discrepancies during integrity verification.
<<<
COMMENT: Baselines: High
BASELINE: High
STATUS: Draft

[REQUIREMENT]
UID: SI-7.3
TITLE: SI-7(3) Centrally Managed Integrity Tools
STATEMENT: >>>
Employ centrally managed integrity verification tools.
<<<
BASELINE: None
STATUS: Draft

[REQUIREMENT]
UID: SI-7.4
TITLE: SI-7(4) Tamper-evident Packaging
STATEMENT: >>>
Withdrawn. Incorporated into SR-9.
<<<
COMMENT: Withdrawn
BASELINE: None
STATUS: Draft

[REQUIREMENT]
UID: SI-7.5
TITLE: SI-7(5) Automated Response to Integrity Violations
STATEMENT: >>>
Automatically [si-07.05_odp.01] when integrity violations are discovered.
<<<
COMMENT: Baselines: High
BASELINE: High
STATUS: Draft

[REQUIREMENT]
UID: SI-7.6
TITLE: SI-7(6) Cryptographic Protection
STATEMENT: >>>
Implement cryptographic mechanisms to detect unauthorized changes to software, firmware, and information.
<<<
BASELINE: None
STATUS: Draft

[REQUIREMENT]
UID: SI-7.7
TITLE: SI-7(7) Integration of Detection and Response
STATEMENT: >>>
Incorporate the detection of the following unauthorized changes into the organizational incident response capability: [changes].
<<<
COMMENT: Baselines: Moderate, High
BASELINE: Moderate
STATUS: Draft

[REQUIREMENT]
UID: SI-7.8
TITLE: SI-7(8) Auditing Capability for Significant Events
STATEMENT: >>>
Upon detection of a potential integrity violation, provide the capability to audit the event and initiate the following actions: [si-07.08_odp.01].
<<<
BASELINE: None
STATUS: Draft

[REQUIREMENT]
UID: SI-7.9
TITLE: SI-7(9) Verify Boot Process
STATEMENT: >>>
Verify the integrity of the boot process of the following system components: [system components].
<<<
BASELINE: None
STATUS: Draft

[REQUIREMENT]
UID: SI-7.10
TITLE: SI-7(10) Protection of Boot Firmware
STATEMENT: >>>
Implement the following mechanisms to protect the integrity of boot firmware in [system components]: [mechanisms].
<<<
BASELINE: None
STATUS: Draft

[REQUIREMENT]
UID: SI-7.11
TITLE: SI-7(11) Confined Environments with Limited Privileges
STATEMENT: >>>
Withdrawn.
<<<
COMMENT: Withdrawn
BASELINE: None
STATUS: Draft

[REQUIREMENT]
UID: SI-7.12
TITLE: SI-7(12) Integrity Verification
STATEMENT: >>>
Require that the integrity of the following user-installed software be verified prior to execution: [user-installed software].
<<<
BASELINE: None
STATUS: Draft

[REQUIREMENT]
UID: SI-7.13
TITLE: SI-7(13) Code Execution in Protected Environments
STATEMENT: >>>
Withdrawn.
<<<
COMMENT: Withdrawn
BASELINE: None
STATUS: Draft

[REQUIREMENT]
UID: SI-7.14
TITLE: SI-7(14) Binary or Machine Executable Code
STATEMENT: >>>
Withdrawn.
<<<
COMMENT: Withdrawn
BASELINE: None
STATUS: Draft

[REQUIREMENT]
UID: SI-7.15
TITLE: SI-7(15) Code Authentication
STATEMENT: >>>
Implement cryptographic mechanisms to authenticate the following software or firmware components prior to installation: [software or firmware components].
<<<
COMMENT: Baselines: High
BASELINE: High
STATUS: Draft

[REQUIREMENT]
UID: SI-7.16
TITLE: SI-7(16) Time Limit on Process Execution Without Supervision
STATEMENT: >>>
Prohibit processes from executing without supervision for more than [time period].
<<<
BASELINE: None
STATUS: Draft

[REQUIREMENT]
UID: SI-7.17
TITLE: SI-7(17) Runtime Application Self-protection
STATEMENT: >>>
Implement [controls] for application self-protection at runtime.
<<<
BASELINE: None
STATUS: Draft

[REQUIREMENT]
UID: SI-8
TITLE: SI-8 Spam Protection
STATEMENT: >>>
a. Employ spam protection mechanisms at system entry and exit points to detect and act on unsolicited messages; and

b. Update spam protection mechanisms when new releases are available in accordance with organizational configuration management policy and procedures.
<<<
COMMENT: Baselines: Moderate, High
BASELINE: Moderate
STATUS: Draft

[REQUIREMENT]
UID: SI-8.1
TITLE: SI-8(1) Central Management
STATEMENT: >>>
Withdrawn. Incorporated into PL-9.
<<<
COMMENT: Withdrawn
BASELINE: None
STATUS: Draft

[REQUIREMENT]
UID: SI-8.2
TITLE: SI-8(2) Automatic Updates
STATEMENT: >>>
Automatically update spam protection mechanisms [frequency].
<<<
COMMENT: Baselines: Moderate, High
BASELINE: Moderate
STATUS: Draft

[REQUIREMENT]
UID: SI-8.3
TITLE: SI-8(3) Continuous Learning Capability
STATEMENT: >>>
Implement spam protection mechanisms with a learning capability to more effectively identify legitimate communications traffic.
<<<
BASELINE: None
STATUS: Draft

[REQUIREMENT]
UID: SI-9
TITLE: SI-9 Information Input Restrictions
STATEMENT: >>>
Withdrawn. Incorporated into AC-2, AC-3, AC-5, AC-6.
<<<
COMMENT: Withdrawn
BASELINE: None
STATUS: Draft

[REQUIREMENT]
UID: SI-10
TITLE: SI-10 Information Input Validation
STATEMENT: >>>
Check the validity of the following information inputs: [information inputs].
<<<
COMMENT: Baselines: Moderate, High
BASELINE: Moderate
STATUS: Draft

[REQUIREMENT]
UID: SI-10.1
TITLE: SI-10(1) Manual Override Capability
STATEMENT: >>>
(a) Provide a manual override capability for input validation of the following information inputs: [si-10_odp];

(b) Restrict the use of the manual override capability to only [authorized individuals] ; and

(c) Audit the use of the manual override capability.
<<<
BASELINE: None
STATUS: Draft

[REQUIREMENT]
UID: SI-10.2
TITLE: SI-10(2) Review and Resolve Errors
STATEMENT: >>>
Review and resolve input validation errors within [organization-defined time period].
<<<
BASELINE: None
STATUS: Draft

[REQUIREMENT]
UID: SI-10.3
TITLE: SI-10(3) Predictable Behavior
STATEMENT: >>>
Verify that the system behaves in a predictable and documented manner when invalid inputs are received.
<<<
BASELINE: None
STATUS: Draft

[REQUIREMENT]
UID: SI-10.4
TITLE: SI-10(4) Timing Interactions
STATEMENT: >>>
Account for timing interactions among system components in determining appropriate responses for invalid inputs.
<<<
BASELINE: None
STATUS: Draft

[REQUIREMENT]
UID: SI-10.5
TITLE: SI-10(5) Restrict Inputs to Trusted Sources and Approved Formats
STATEMENT: >>>
Restrict the use of information inputs to [trusted sources] and/or [formats].
<<<
BASELINE: None
STATUS: Draft

[REQUIREMENT]
UID: SI-10.6
TITLE: SI-10(6) Injection Prevention
STATEMENT: >>>
Prevent untrusted data injections.
<<<
BASELINE: None
STATUS: Draft

[REQUIREMENT]
UID: SI-11
TITLE: SI-11 Error Handling
STATEMENT: >>>
a. Generate error messages that provide information necessary for corrective actions without revealing information that could be exploited; and

b. Reveal error messages only to [personnel or roles].
<<<
COMMENT: Baselines: Moderate, High
BASELINE: Moderate
STATUS: Draft

[REQUIREMENT]
UID: SI-12
TITLE: SI-12 Information Management and Retention
STATEMENT: >>>
Manage and retain information within the system and information output from the system in accordance with applicable laws, executive orders, directives, regulations, policies, standards, guidelines and operational requirements.
<<<
COMMENT: Baselines: Low, Moderate, High, Privacy
BASELINE: Low
STATUS: Draft

[REQUIREMENT]
UID: SI-12.1
TITLE: SI-12(1) Limit Personally Identifiable Information Elements
STATEMENT: >>>
Limit personally identifiable information being processed in the information life cycle to the following elements of personally identifiable information: [elements of personally identifiable information].
<<<
COMMENT: Baselines: Privacy
BASELINE: Privacy
STATUS: Draft

[REQUIREMENT]
UID: SI-12.2
TITLE: SI-12(2) Minimize Personally Identifiable Information in Testing, Training, and Research
STATEMENT: >>>
Use the following techniques to minimize the use of personally identifiable information for research, testing, or training: [organization-defined techniques].
<<<
COMMENT: Baselines: Privacy
BASELINE: Privacy
STATUS: Draft

[REQUIREMENT]
UID: SI-12.3
TITLE: SI-12(3) Information Disposal
STATEMENT: >>>
Use the following techniques to dispose of, destroy, or erase information following the retention period: [organization-defined techniques].
<<<
COMMENT: Baselines: Privacy
BASELINE: Privacy
STATUS: Draft

[REQUIREMENT]
UID: SI-13
TITLE: SI-13 Predictable Failure Prevention
STATEMENT: >>>
a. Determine mean time to failure (MTTF) for the following system components in specific environments of operation: [system components] ; and

b. Provide substitute system components and a means to exchange active and standby components in accordance with the following criteria: [mean time to failure (MTTF) substitution criteria].
<<<
BASELINE: None
STATUS: Draft

[REQUIREMENT]
UID: SI-13.1
TITLE: SI-13(1) Transferring Component Responsibilities
STATEMENT: >>>
Take system components out of service by transferring component responsibilities to substitute components no later than [fraction or percentage] of mean time to failure.
<<<
BASELINE: None
STATUS: Draft

[REQUIREMENT]
UID: SI-13.2
TITLE: SI-13(2) Time Limit on Process Execution Without Supervision
STATEMENT: >>>
Withdrawn. Incorporated into SI-7.16.
<<<
COMMENT: Withdrawn
BASELINE: None
STATUS: Draft

[REQUIREMENT]
UID: SI-13.3
TITLE: SI-13(3) Manual Transfer Between Components
STATEMENT: >>>
Manually initiate transfers between active and standby system components when the use of the active component reaches [percentage] of the mean time to failure.
<<<
BASELINE: None
STATUS: Draft

[REQUIREMENT]
UID: SI-13.4
TITLE: SI-13(4) Standby Component Installation and Notification
STATEMENT: >>>
If system component failures are detected:

  (a) Ensure that the standby components are successfully and transparently installed within [time period] ; and

  (b) [si-13.04_odp.02].
<<<
BASELINE: None
STATUS: Draft

[REQUIREMENT]
UID: SI-13.5
TITLE: SI-13(5) Failover Capability
STATEMENT: >>>
Provide [si-13.05_odp.01] [failover capability] for the system.
<<<
BASELINE: None
STATUS: Draft

[REQUIREMENT]
UID: SI-14
TITLE: SI-14 Non-persistence
STATEMENT: >>>
Implement non-persistent [system components and services] that are initiated in a known state and terminated [si-14_odp.02].
<<<
BASELINE: None
STATUS: Draft

[REQUIREMENT]
UID: SI-14.1
TITLE: SI-14(1) Refresh from Trusted Sources
STATEMENT: >>>
Obtain software and data employed during system component and service refreshes from the following trusted sources: [trusted sources].
<<<
BASELINE: None
STATUS: Draft

[REQUIREMENT]
UID: SI-14.2
TITLE: SI-14(2) Non-persistent Information
STATEMENT: >>>
(a) [si-14.02_odp.01] ; and

(b) Delete information when no longer needed.
<<<
BASELINE: None
STATUS: Draft

[REQUIREMENT]
UID: SI-14.3
TITLE: SI-14(3) Non-persistent Connectivity
STATEMENT: >>>
Establish connections to the system on demand and terminate connections after [si-14.03_odp].
<<<
BASELINE: None
STATUS: Draft

[REQUIREMENT]
UID: SI-15
TITLE: SI-15 Information Output Filtering
STATEMENT: >>>
Validate information output from the following software programs and/or applications to ensure that the information is consistent with the expected content: [software programs and/or applications].
<<<
BASELINE: None
STATUS: Draft

[REQUIREMENT]
UID: SI-16
TITLE: SI-16 Memory Protection
STATEMENT: >>>
Implement the following controls to protect the system memory from unauthorized code execution: [controls].
<<<
COMMENT: Baselines: Moderate, High
BASELINE: Moderate
STATUS: Draft

[REQUIREMENT]
UID: SI-17
TITLE: SI-17 Fail-safe Procedures
STATEMENT: >>>
Implement the indicated fail-safe procedures when the indicated failures occur: [organization-defined list of failure conditions and associated fail-safe procedures].
<<<
BASELINE: None
STATUS: Draft

[REQUIREMENT]
UID: SI-18
TITLE: SI-18 Personally Identifiable Information Quality Operations
STATEMENT: >>>
a. Check the accuracy, relevance, timeliness, and completeness of personally identifiable information across the information life cycle [organization-defined frequency] ; and

b. Correct or delete inaccurate or outdated personally identifiable information.
<<<
COMMENT: Baselines: Privacy
BASELINE: Privacy
STATUS: Draft

[REQUIREMENT]
UID: SI-18.1
TITLE: SI-18(1) Automation Support
STATEMENT: >>>
Correct or delete personally identifiable information that is inaccurate or outdated, incorrectly determined regarding impact, or incorrectly de-identified using [automated mechanisms].
<<<
BASELINE: None
STATUS: Draft

[REQUIREMENT]
UID: SI-18.2
TITLE: SI-18(2) Data Tags
STATEMENT: >>>
Employ data tags to automate the correction or deletion of personally identifiable information across the information life cycle within organizational systems.
<<<
BASELINE: None
STATUS: Draft

[REQUIREMENT]
UID: SI-18.3
TITLE: SI-18(3) Collection
STATEMENT: >>>
Collect personally identifiable information directly from the individual.
<<<
BASELINE: None
STATUS: Draft

[REQUIREMENT]
UID: SI-18.4
TITLE: SI-18(4) Individual Requests
STATEMENT: >>>
Correct or delete personally identifiable information upon request by individuals or their designated representatives.
<<<
COMMENT: Baselines: Privacy
BASELINE: Privacy
STATUS: Draft

[REQUIREMENT]
UID: SI-18.5
TITLE: SI-18(5) Notice of Correction or Deletion
STATEMENT: >>>
Notify [recipients] and individuals that the personally identifiable information has been corrected or deleted.
<<<
BASELINE: None
STATUS: Draft

[REQUIREMENT]
UID: SI-19
TITLE: SI-19 De-identification
STATEMENT: >>>
a. Remove the following elements of personally identifiable information from datasets: [elements] ; and

b. Evaluate [frequency] for effectiveness of de-identification.
<<<
COMMENT: Baselines: Privacy
BASELINE: Privacy
STATUS: Draft

[REQUIREMENT]
UID: SI-19.1
TITLE: SI-19(1) Collection
STATEMENT: >>>
De-identify the dataset upon collection by not collecting personally identifiable information.
<<<
BASELINE: None
STATUS: Draft

[REQUIREMENT]
UID: SI-19.2
TITLE: SI-19(2) Archiving
STATEMENT: >>>
Prohibit archiving of personally identifiable information elements if those elements in a dataset will not be needed after the dataset is archived.
<<<
BASELINE: None
STATUS: Draft

[REQUIREMENT]
UID: SI-19.3
TITLE: SI-19(3) Release
STATEMENT: >>>
Remove personally identifiable information elements from a dataset prior to its release if those elements in the dataset do not need to be part of the data release.
<<<
BASELINE: None
STATUS: Draft

[REQUIREMENT]
UID: SI-19.4
TITLE: SI-19(4) Removal, Masking, Encryption, Hashing, or Replacement of Direct Identifiers
STATEMENT: >>>
Remove, mask, encrypt, hash, or replace direct identifiers in a dataset.
<<<
BASELINE: None
STATUS: Draft

[REQUIREMENT]
UID: SI-19.5
TITLE: SI-19(5) Statistical Disclosure Control
STATEMENT: >>>
Manipulate numerical data, contingency tables, and statistical findings so that no individual or organization is identifiable in the results of the analysis.
<<<
BASELINE: None
STATUS: Draft

[REQUIREMENT]
UID: SI-19.6
TITLE: SI-19(6) Differential Privacy
STATEMENT: >>>
Prevent disclosure of personally identifiable information by adding non-deterministic noise to the results of mathematical operations before the results are reported.
<<<
BASELINE: None
STATUS: Draft

[REQUIREMENT]
UID: SI-19.7
TITLE: SI-19(7) Validated Algorithms and Software
STATEMENT: >>>
Perform de-identification using validated algorithms and software that is validated to implement the algorithms.
<<<
BASELINE: None
STATUS: Draft

[REQUIREMENT]
UID: SI-19.8
TITLE: SI-19(8) Motivated Intruder
STATEMENT: >>>
Perform a motivated intruder test on the de-identified dataset to determine if the identified data remains or if the de-identified data can be re-identified.
<<<
BASELINE: None
STATUS: Draft

[REQUIREMENT]
UID: SI-20
TITLE: SI-20 Tainting
STATEMENT: >>>
Embed data or capabilities in the following systems or system components to determine if organizational data has been exfiltrated or improperly removed from the organization: [systems or system components].
<<<
BASELINE: None
STATUS: Draft

[REQUIREMENT]
UID: SI-21
TITLE: SI-21 Information Refresh
STATEMENT: >>>
Refresh [information] at [frequencies] or generate the information on demand and delete the information when no longer needed.
<<<
BASELINE: None
STATUS: Draft

[REQUIREMENT]
UID: SI-22
TITLE: SI-22 Information Diversity
STATEMENT: >>>
a. Identify the following alternative sources of information for [essential functions and services]: [alternative information sources] ; and

b. Use an alternative information source for the execution of essential functions or services on [systems or system components] when the primary source of information is corrupted or unavailable.
<<<
BASELINE: None
STATUS: Draft

[REQUIREMENT]
UID: SI-23
TITLE: SI-23 Information Fragmentation
STATEMENT: >>>
Based on [circumstances]:

  a. Fragment the following information: [information] ; and

  b. Distribute the fragmented information across the following systems or system components: [systems or system components].
<<<
BASELINE: None
STATUS: Draft

[[/SECTION]]

[[SECTION]]
UID: NIST-SR
TITLE: SR — Supply Chain Risk Management

[REQUIREMENT]
UID: SR-1
TITLE: SR-1 Policy and Procedures
STATEMENT: >>>
a. Develop, document, and disseminate to [organization-defined personnel or roles]:

  1. [sr-01_odp.03] supply chain risk management policy that:

    (a) Addresses purpose, scope, roles, responsibilities, management commitment, coordination among organizational entities, and compliance; and

    (b) Is consistent with applicable laws, executive orders, directives, regulations, policies, standards, and guidelines; and

  2. Procedures to facilitate the implementation of the supply chain risk management policy and the associated supply chain risk management controls;

b. Designate an [official] to manage the development, documentation, and dissemination of the supply chain risk management policy and procedures; and

c. Review and update the current supply chain risk management:

  1. Policy [frequency] and following [events] ; and

  2. Procedures [frequency] and following [events].
<<<
COMMENT: Baselines: Low, Moderate, High
BASELINE: Low
STATUS: Draft

[REQUIREMENT]
UID: SR-2
TITLE: SR-2 Supply Chain Risk Management Plan
STATEMENT: >>>
a. Develop a plan for managing supply chain risks associated with the research and development, design, manufacturing, acquisition, delivery, integration, operations and maintenance, and disposal of the following systems, system components or system services: [systems, system components, or system services];

b. Review and update the supply chain risk management plan [frequency] or as required, to address threat, organizational or environmental changes; and

c. Protect the supply chain risk management plan from unauthorized disclosure and modification.
<<<
COMMENT: Baselines: Low, Moderate, High
BASELINE: Low
STATUS: Draft

[REQUIREMENT]
UID: SR-2.1
TITLE: SR-2(1) Establish SCRM Team
STATEMENT: >>>
Establish a supply chain risk management team consisting of [personnel, roles and responsibilities] to lead and support the following SCRM activities: [supply chain risk management activities].
<<<
COMMENT: Baselines: Low, Moderate, High
BASELINE: Low
STATUS: Draft

[REQUIREMENT]
UID: SR-3
TITLE: SR-3 Supply Chain Controls and Processes
STATEMENT: >>>
a. Establish a process or processes to identify and address weaknesses or deficiencies in the supply chain elements and processes of [system or system component] in coordination with [supply chain personnel];

b. Employ the following controls to protect against supply chain risks to the system, system component, or system service and to limit the harm or consequences from supply chain-related events: [supply chain controls] ; and

c. Document the selected and implemented supply chain processes and controls in [sr-03_odp.04].
<<<
COMMENT: Baselines: Low, Moderate, High
BASELINE: Low
STATUS: Draft

[REQUIREMENT]
UID: SR-3.1
TITLE: SR-3(1) Diverse Supply Base
STATEMENT: >>>
Employ a diverse set of sources for the following system components and services: [organization-defined system components and services].
<<<
BASELINE: None
STATUS: Draft

[REQUIREMENT]
UID: SR-3.2
TITLE: SR-3(2) Limitation of Harm
STATEMENT: >>>
Employ the following controls to limit harm from potential adversaries identifying and targeting the organizational supply chain: [controls].
<<<
BASELINE: None
STATUS: Draft

[REQUIREMENT]
UID: SR-3.3
TITLE: SR-3(3) Sub-tier Flow Down
STATEMENT: >>>
Ensure that the controls included in the contracts of prime contractors are also included in the contracts of subcontractors.
<<<
BASELINE: None
STATUS: Draft

[REQUIREMENT]
UID: SR-4
TITLE: SR-4 Provenance
STATEMENT: >>>
Document, monitor, and maintain valid provenance of the following systems, system components, and associated data: [systems, system components, and associated data].
<<<
BASELINE: None
STATUS: Draft

[REQUIREMENT]
UID: SR-4.1
TITLE: SR-4(1) Identity
STATEMENT: >>>
Establish and maintain unique identification of the following supply chain elements, processes, and personnel associated with the identified system and critical system components: [supply chain elements, processes, and personnel].
<<<
BASELINE: None
STATUS: Draft

[REQUIREMENT]
UID: SR-4.2
TITLE: SR-4(2) Track and Trace
STATEMENT: >>>
Establish and maintain unique identification of the following systems and critical system components for tracking through the supply chain: [systems and critical system components].
<<<
BASELINE: None
STATUS: Draft

[REQUIREMENT]
UID: SR-4.3
TITLE: SR-4(3) Validate as Genuine and Not Altered
STATEMENT: >>>
Employ the following controls to validate that the system or system component received is genuine and has not been altered: [organization-defined controls].
<<<
BASELINE: None
STATUS: Draft

[REQUIREMENT]
UID: SR-4.4
TITLE: SR-4(4) Supply Chain Integrity — Pedigree
STATEMENT: >>>
Employ [controls] and conduct [analysis method] to ensure the integrity of the system and system components by validating the internal composition and provenance of critical or mission-essential technologies, products, and services.
<<<
BASELINE: None
STATUS: Draft

[REQUIREMENT]
UID: SR-5
TITLE: SR-5 Acquisition Strategies, Tools, and Methods
STATEMENT: >>>
Employ the following acquisition strategies, contract tools, and procurement methods to protect against, identify, and mitigate supply chain risks: [strategies, tools, and methods].
<<<
COMMENT: Baselines: Low, Moderate, High
BASELINE: Low
STATUS: Draft

[REQUIREMENT]
UID: SR-5.1
TITLE: SR-5(1) Adequate Supply
STATEMENT: >>>
Employ the following controls to ensure an adequate supply of [critical system components]: [controls].
<<<
BASELINE: None
STATUS: Draft

[REQUIREMENT]
UID: SR-5.2
TITLE: SR-5(2) Assessments Prior to Selection, Acceptance, Modification, or Update
STATEMENT: >>>
Assess the system, system component, or system service prior to selection, acceptance, modification, or update.
<<<
BASELINE: None
STATUS: Draft

[REQUIREMENT]
UID: SR-6
TITLE: SR-6 Supplier Assessments and Reviews
STATEMENT: >>>
Assess and review the supply chain-related risks associated with suppliers or contractors and the system, system component, or system service they provide [frequency].
<<<
COMMENT: Baselines: Moderate, High
BASELINE: Moderate
STATUS: Draft

[REQUIREMENT]
UID: SR-6.1
TITLE: SR-6(1) Testing and Analysis
STATEMENT: >>>
Employ [sr-06.01_odp.01] of the following supply chain elements, processes, and actors associated with the system, system component, or system service: [supply chain elements, processes, and actors].
<<<
BASELINE: None
STATUS: Draft

[REQUIREMENT]
UID: SR-7
TITLE: SR-7 Supply Chain Operations Security
STATEMENT: >>>
Employ the following Operations Security (OPSEC) controls to protect supply chain-related information for the system, system component, or system service: [OPSEC controls].
<<<
BASELINE: None
STATUS: Draft

[REQUIREMENT]
UID: SR-8
TITLE: SR-8 Notification Agreements
STATEMENT: >>>
Establish agreements and procedures with entities involved in the supply chain for the system, system component, or system service for the [sr-08_odp.01].
<<<
COMMENT: Baselines: Low, Moderate, High
BASELINE: Low
STATUS: Draft

[REQUIREMENT]
UID: SR-9
TITLE: SR-9 Tamper Resistance and Detection
STATEMENT: >>>
Implement a tamper protection program for the system, system component, or system service.
<<<
COMMENT: Baselines: High
BASELINE: High
STATUS: Draft

[REQUIREMENT]
UID: SR-9.1
TITLE: SR-9(1) Multiple Stages of System Development Life Cycle
STATEMENT: >>>
Employ anti-tamper technologies, tools, and techniques throughout the system development life cycle.
<<<
COMMENT: Baselines: High
BASELINE: High
STATUS: Draft

[REQUIREMENT]
UID: SR-10
TITLE: SR-10 Inspection of Systems or Components
STATEMENT: >>>
Inspect the following systems or system components [sr-10_odp.02] to detect tampering: [systems or system components].
<<<
COMMENT: Baselines: Low, Moderate, High
BASELINE: Low
STATUS: Draft

[REQUIREMENT]
UID: SR-11
TITLE: SR-11 Component Authenticity
STATEMENT: >>>
a. Develop and implement anti-counterfeit policy and procedures that include the means to detect and prevent counterfeit components from entering the system; and

b. Report counterfeit system components to [sr-11_odp.01].
<<<
COMMENT: Baselines: Low, Moderate, High
BASELINE: Low
STATUS: Draft

[REQUIREMENT]
UID: SR-11.1
TITLE: SR-11(1) Anti-counterfeit Training
STATEMENT: >>>
Train [personnel or roles] to detect counterfeit system components (including hardware, software, and firmware).
<<<
COMMENT: Baselines: Low, Moderate, High
BASELINE: Low
STATUS: Draft

[REQUIREMENT]
UID: SR-11.2
TITLE: SR-11(2) Configuration Control for Component Service and Repair
STATEMENT: >>>
Maintain configuration control over the following system components awaiting service or repair and serviced or repaired components awaiting return to service: [system components].
<<<
COMMENT: Baselines: Low, Moderate, High
BASELINE: Low
STATUS: Draft

[REQUIREMENT]
UID: SR-11.3
TITLE: SR-11(3) Anti-counterfeit Scanning
STATEMENT: >>>
Scan for counterfeit system components [frequency].
<<<
BASELINE: None
STATUS: Draft

[REQUIREMENT]
UID: SR-12
TITLE: SR-12 Component Disposal
STATEMENT: >>>
Dispose of [data, documentation, tools, or system components] using the following techniques and methods: [techniques and methods].
<<<
COMMENT: Baselines: Low, Moderate, High
BASELINE: Low
STATUS: Draft

[[/SECTION]]
