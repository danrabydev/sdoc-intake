[DOCUMENT]
TITLE: System Requirements
UID: PRODUCT-SYS
PREFIX: SYS-
ROOT: True

[GRAMMAR]
ELEMENTS:
- TAG: TEXT
  FIELDS:
  - TITLE: STATEMENT
    TYPE: String
    REQUIRED: True
- TAG: SECTION
  PROPERTIES:
    IS_COMPOSITE: True
  FIELDS:
  - TITLE: UID
    TYPE: String
    REQUIRED: False
  - TITLE: PREFIX
    TYPE: String
    REQUIRED: False
  - TITLE: TITLE
    TYPE: String
    REQUIRED: True
- TAG: REQUIREMENT
  FIELDS:
  - TITLE: UID
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  - TITLE: STATUS
    TYPE: SingleChoice(Draft, Active, Approved)
    REQUIRED: False
  RELATIONS:
  - TYPE: Parent
  - TYPE: Child
  - TYPE: File
  - TYPE: Parent
    ROLE: Refines
  - TYPE: Parent
    ROLE: Satisfies
  - TYPE: Parent
    ROLE: Uses
  - TYPE: Parent
    ROLE: ConformsTo

[[SECTION]]
UID: SYS-SEC-002
TITLE: New section

[REQUIREMENT]
UID: SYS-031
TITLE: New requirement
RELATIONS:
- TYPE: Parent
  ROLE: Refines
  VALUE: CTRL-NIST-001

[[SECTION]]
UID: SYS-SEC-003
TITLE: Authentication
PREFIX: AUTHz

[REQUIREMENT]
UID: SYS-AUTHz-032
TITLE: Single Sign-On

[REQUIREMENT]
UID: SYS-AUTHz-033
TITLE: New requirement

[REQUIREMENT]
UID: SYS-AUTHz-034
TITLE: New requirement

[REQUIREMENT]
UID: SYS-AUTH-035
TITLE: New requirement

[REQUIREMENT]
UID: SYS-AUTH-036
TITLE: New requirement
[[/SECTION]]

[[SECTION]]
UID: SYS-SEC-004
TITLE: New section
[[/SECTION]]
[[/SECTION]]
