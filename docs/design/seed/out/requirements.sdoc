[DOCUMENT]
TITLE: ReqALM — Requirements
UID: reqalm-requirements
VERSION: 2026-10-07
OPTIONS:
  MARKUP: Text
METADATA:
  client: Raby-Family (raby-family)
  project: ReqALM (reqalm)
  schema_version: 2026-10-07
  note: ReqALM dogfood export — StrictDoc interchange only

[GRAMMAR]
ELEMENTS:
- TAG: TEXT
  FIELDS:
  - TITLE: UID
    TYPE: String
    REQUIRED: False
  - TITLE: STATEMENT
    TYPE: String
    REQUIRED: True
- TAG: REQUIREMENT
  FIELDS:
  - TITLE: UID
    TYPE: String
    REQUIRED: True
  - TITLE: STATUS
    TYPE: String
    REQUIRED: False
  - TITLE: TITLE
    TYPE: String
    REQUIRED: False
  - TITLE: STATEMENT
    TYPE: String
    REQUIRED: True
  - TITLE: COMMENT
    TYPE: String
    REQUIRED: False
  RELATIONS:
  - TYPE: Parent
  - TYPE: Parent
    ROLE: Satisfies
  - TYPE: Parent
    ROLE: ConformsTo
  - TYPE: Parent
    ROLE: Uses
  - TYPE: Parent
    ROLE: Refines
  - TYPE: Parent
    ROLE: InScopeOf
    REVERSE_ROLE: InScopeOf
  - TYPE: Parent
    ROLE: Delivers
    REVERSE_ROLE: Delivers
  - TYPE: Child
  - TYPE: Child
    ROLE: Satisfies
  - TYPE: Child
    ROLE: ConformsTo
  - TYPE: Child
    ROLE: Uses
  - TYPE: Child
    ROLE: Refines
  - TYPE: Child
    ROLE: InScopeOf
  - TYPE: Child
    ROLE: Delivers
  - TYPE: File

[[SECTION]]
UID: SEC-IA
TITLE: Identity & Access

[TEXT]
UID: SEC-IA-INTRO
STATEMENT: >>>
Identity and access actions for ReqAML — SSO sign-in/out, client scoped view, profile, project grant administration, and catalog-steward grants.
<<<

[REQUIREMENT]
UID: A01
STATUS: Active
TITLE: Sign in via SSO
STATEMENT: >>>
A user signs in via enterprise SSO (OIDC or SAML). ReqAML validates the IdP token,
establishes a least-privilege session, loads project grants, and emits an auditable sign-in event.
No local password store exists; MFA is enforced at the IdP. Downstream APIs reject callers without a valid session.
<<<
COMMENT: >>>
KIND: requirement
BASE_UID: A01
VERSION_N: 0
rbac_op: auth:signin
priority: 10
iteration: iter-r0
security.catalog_ref: IA-2
security.verification_note: IA-2 / AC-3 / AU-2/3/12. ASD STIG V6R4 V-222536 (password length IdP-delegated); no local passwords; MFA at IdP.
edge: ← satisfies from CAP-SSO
edge: ← refines from ARCH-OTEL
edge: ← refines from MC01.1
edge: ← refines from ARCH-DEVENV-IDENTITY
edge: ← uses from FIX-DENY-DEVENV-PROD-LOGIN
edge: ← refines from ARCH-DEVENV-IDENTITY.1
edge: ← uses from FIX-DENY-DEVENV-PROD-LOGIN.1
edge: ← refines from ARCH-AUTH-AS
edge: ← refines from ARCH-AUTH-FEDERATION
edge: ← uses from FIX-ALLOW-FEDERATED-SSO-VIA-AS
edge: ← refines from ARCH-AUTH-LOCAL.1
edge: ← refines from ARCH-AUTH-PROFILE
edge: ← uses from FIX-DENY-LOCAL-LOGIN-PROFILE-OFF
edge: ← satisfies from CAP-SSO.1
in_scope_of_contract: Design-2026-10
in_scope_of_contract: Security package
in_scope_of_contract: Platform baseline
in_scope_of_contract: Legacy intake (closed)
in_scope_of_contract: Fixture doc-walk
in_scope_of_contract: ReqALM product (build)
delivered_by_release: R0-sequences
edge: → conforms_to to AC-3 (pin imprint=nist-800-53@rev5-dogfood-20261006)
edge: → conforms_to to IA-2 (pin imprint=nist-800-53@rev5-dogfood-20261006)
edge: → conforms_to to SC-8 (pin imprint=nist-800-53@rev5-dogfood-20261006)
edge: → conforms_to to V-222536 (pin imprint=asd-stig@v6r4)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-IA
- TYPE: Parent
  VALUE: AC-3
  ROLE: ConformsTo
- TYPE: Parent
  VALUE: IA-2
  ROLE: ConformsTo
- TYPE: Parent
  VALUE: SC-8
  ROLE: ConformsTo
- TYPE: Parent
  VALUE: V-222536
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-security-package
  ROLE: InScopeOf
- TYPE: Child
  VALUE: CONTRACT-contract-platform-baseline
  ROLE: InScopeOf
- TYPE: Child
  VALUE: CONTRACT-contract-legacy-intake-closed
  ROLE: InScopeOf
- TYPE: Child
  VALUE: CONTRACT-contract-fixture-doc-walk
  ROLE: InScopeOf
- TYPE: Child
  VALUE: CONTRACT-ctr-reqalm-product
  ROLE: InScopeOf
- TYPE: Child
  VALUE: RELEASE-rel-r0-sequences
  ROLE: Delivers

[REQUIREMENT]
UID: A02
STATUS: Active
TITLE: Sign out
STATEMENT: >>>
An authenticated user signs out. ReqAML terminates the server session, clears the client session handle,
revokes any desk attachments for that session, and records an auditable logout event.
Subsequent API calls with the old handle receive an unauthorized outcome.
<<<
COMMENT: >>>
KIND: requirement
BASE_UID: A02
VERSION_N: 0
rbac_op: auth:signout
priority: 20
iteration: iter-r0
security.catalog_ref: AC-12
security.verification_note: AC-12 session termination; AU-2/3/12 logout audit. ASD STIG V6R4 V-222578 / V-222391 / V-222550.
edge: ← satisfies from CAP-SSO
edge: ← refines from ARCH-AUTH-REVOKE
edge: ← refines from ARCH-CRED-SESSION
edge: ← uses from FIX-DENY-REVOKED-TOKEN
edge: ← satisfies from CAP-SSO.1
in_scope_of_contract: Design-2026-10
in_scope_of_contract: Security package
in_scope_of_contract: Fixture doc-walk
in_scope_of_contract: ReqALM product (build)
delivered_by_release: R0-sequences
edge: → conforms_to to AC-12 (pin imprint=nist-800-53@rev5-dogfood-20261006)
edge: → conforms_to to V-222578 (pin imprint=asd-stig@v6r4)
edge: → conforms_to to V-222391 (pin imprint=asd-stig@v6r4)
edge: → conforms_to to V-222550 (pin imprint=asd-stig@v6r4)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-IA
- TYPE: Parent
  VALUE: AC-12
  ROLE: ConformsTo
- TYPE: Parent
  VALUE: V-222578
  ROLE: ConformsTo
- TYPE: Parent
  VALUE: V-222391
  ROLE: ConformsTo
- TYPE: Parent
  VALUE: V-222550
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-security-package
  ROLE: InScopeOf
- TYPE: Child
  VALUE: CONTRACT-contract-fixture-doc-walk
  ROLE: InScopeOf
- TYPE: Child
  VALUE: CONTRACT-ctr-reqalm-product
  ROLE: InScopeOf
- TYPE: Child
  VALUE: RELEASE-rel-r0-sequences
  ROLE: Delivers

[REQUIREMENT]
UID: A03
STATUS: Active
TITLE: Select Client Scoped View
STATEMENT: >>>
An authenticated user selects a Client Scoped View. The active clientId is persisted server-side so
subsequent queries and mutations are bound to that client for least privilege.
The UI App shell reads the bound clientId from the session; client-side-only scope is not authoritative.
<<<
COMMENT: >>>
KIND: requirement
BASE_UID: A03
VERSION_N: 0
rbac_op: client:scope:select
priority: 10
iteration: iter-r0
security.catalog_ref: AC-3
security.verification_note: AC-3/AC-6 least privilege via server-bound scope. ASD STIG V6R4 V-222429 / V-222550.
edge: ← satisfies from CAP-SCOPED-VIEW
edge: ← uses from B08
edge: ← satisfies from CAP-SCOPED-VIEW.1
in_scope_of_contract: Design-2026-10
in_scope_of_contract: Security package
in_scope_of_contract: Platform baseline
in_scope_of_contract: ReqALM product (build)
delivered_by_release: R0-sequences
edge: → conforms_to to AC-3 (pin imprint=nist-800-53@rev5-dogfood-20261006)
edge: → conforms_to to AC-6 (pin imprint=nist-800-53@rev5-dogfood-20261006)
edge: → conforms_to to V-222429 (pin imprint=asd-stig@v6r4)
edge: → conforms_to to V-222550 (pin imprint=asd-stig@v6r4)
<<<
RELATIONS:
- TYPE: Parent
  VALUE: SEC-IA
- TYPE: Parent
  VALUE: AC-3
  ROLE: ConformsTo
- TYPE: Parent
  VALUE: ARCH-CP-HIER
  ROLE: Refines
- TYPE: Parent
  VALUE: ARCH-CP-SCOPE
  ROLE: Refines
- TYPE: Parent
  VALUE: AC-6
  ROLE: ConformsTo
- TYPE: Parent
  VALUE: V-222429
  ROLE: ConformsTo
- TYPE: Parent
  VALUE: V-222550
  ROLE: ConformsTo
- TYPE: Child
  VALUE: CONTRACT-contract-design-2026-10
  ROLE: InScopeOf
- TYPE: Child
  VALUE: CONTRACT-contract-security-package
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r0-sequences
  ROLE: Delivers

[REQUIREMENT]
UID: A04
STATUS: Active
TITLE: Clear / change Scoped View
STATEMENT: >>>
A user clears or changes Client Scoped View. ReqAML updates or clears the server-side active client binding,
invalidates client-scoped caches for the prior binding, and audits the scope change.
Project routes that require a scoped client refuse to proceed until a valid view is selected again.
<<<
COMMENT: >>>
KIND: requirement
BASE_UID: A04
VERSION_N: 0
rbac_op: client:scope:clear
priority: 30
iteration: iter-r0
security.catalog_ref: AC-3
security.verification_note: AC-3 access enforcement on scope clear/change. ASD STIG V6R4 V-222578 / V-222389.
edge: ← satisfies from CAP-SCOPED-VIEW
edge: ← satisfies from CAP-SCOPED-VIEW.1
in_scope_of_contract: Design-2026-10
in_scope_of_contract: Security package
in_scope_of_contract: ReqALM product (build)
delivered_by_release: R0-sequences
edge: → conforms_to to AC-12 (pin imprint=nist-800-53@rev5-dogfood-20261006)
edge: → conforms_to to V-222578 (pin imprint=asd-stig@v6r4)
edge: → conforms_to to V-222389 (pin imprint=asd-stig@v6r4)
edge: → conforms_to to AC-3 (pin imprint=nist-800-53@rev5-dogfood-20261006)
<<<
RELATIONS:
- TYPE: Parent
  VALUE: SEC-IA
- TYPE: Parent
  VALUE: AC-12
  ROLE: ConformsTo
- TYPE: Parent
  VALUE: V-222578
  ROLE: ConformsTo
- TYPE: Parent
  VALUE: V-222389
  ROLE: ConformsTo
- TYPE: Parent
  VALUE: AC-3
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r0-sequences
  ROLE: Delivers

[REQUIREMENT]
UID: A05
STATUS: Active
TITLE: View own profile / grants
STATEMENT: >>>
A user views their own profile and project grants. ReqAML returns only the caller's identity record and
grants (no cross-subject disclosure). Grant role names and project ids are included so the UI can render
authorized navigation without a separate admin call.
<<<
COMMENT: >>>
KIND: requirement
BASE_UID: A05
VERSION_N: 0
rbac_op: identity:read_self
priority: 40
iteration: iter-r0
security.catalog_ref: AC-3
security.verification_note: AC-3 self-read boundary; AU access logging where required. ASD STIG V6R4 V-222430.
edge: ← satisfies from CAP-RBAC
edge: ← satisfies from CAP-RBAC.1
in_scope_of_contract: Design-2026-10
in_scope_of_contract: ReqALM product (build)
delivered_by_release: R0-sequences
edge: → conforms_to to V-222430 (pin imprint=asd-stig@v6r4)
edge: → conforms_to to AC-3 (pin imprint=nist-800-53@rev5-dogfood-20261006)
<<<
RELATIONS:
- TYPE: Parent
  VALUE: SEC-IA
- TYPE: Parent
  VALUE: V-222430
  ROLE: ConformsTo
- TYPE: Parent
  VALUE: AC-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r0-sequences
  ROLE: Delivers

[REQUIREMENT]
UID: A06
STATUS: Active
TITLE: Invite / link identity
STATEMENT: >>>
An admin invites or links an identity to a client or project. ReqAML records the external IdP subject
binding, creates or updates the identity row, and audits who linked whom.
Invitation does not by itself grant project roles; grant create (A07) is a separate mutating step.
<<<
COMMENT: >>>
KIND: requirement
BASE_UID: A06
VERSION_N: 0
rbac_op: identity:link
priority: 50
iteration: iter-r0
security.catalog_ref: IA-2
security.verification_note: IA-2/AC-2 account/identity linkage; AU-2/3/12 admin actions. ASD STIG V6R4 V-222542 / V-222407.
edge: ← satisfies from CAP-RBAC
edge: ← uses from ARCH-AUTH-FEDERATION
edge: ← uses from ARCH-AUTH-UPSTREAM-CONNECTOR
edge: ← uses from ARCH-AUTH-CLAIM-MAP
edge: ← satisfies from CAP-RBAC.1
in_scope_of_contract: Design-2026-10
in_scope_of_contract: Security package
in_scope_of_contract: ReqALM product (build)
delivered_by_release: R0-sequences
edge: → conforms_to to AC-2 (pin imprint=nist-800-53@rev5-dogfood-20261006)
edge: → conforms_to to V-222542 (pin imprint=asd-stig@v6r4)
edge: → conforms_to to V-222407 (pin imprint=asd-stig@v6r4)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to IA-2 (pin imprint=nist-800-53@rev5-dogfood-20261006)
<<<
RELATIONS:
- TYPE: Parent
  VALUE: SEC-IA
- TYPE: Parent
  VALUE: AC-2
  ROLE: ConformsTo
- TYPE: Parent
  VALUE: V-222542
  ROLE: ConformsTo
- TYPE: Parent
  VALUE: V-222407
  ROLE: ConformsTo
- TYPE: Parent
  VALUE: AU-12
  ROLE: ConformsTo
- TYPE: Parent
  VALUE: AU-2
  ROLE: ConformsTo
- TYPE: Parent
  VALUE: AU-3
  ROLE: ConformsTo
- TYPE: Parent
  VALUE: IA-2
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r0-sequences
  ROLE: Delivers

[REQUIREMENT]
UID: A07
STATUS: Active
TITLE: Grant project role
STATEMENT: >>>
A project admin grants a role on a project to an identity. ReqAML creates a project_grant row and audits
the grant (actor, subject, role, project). Duplicate active grants for the same identity+role are rejected.
Effective permissions are evaluated on every subsequent mutating API call.
<<<
COMMENT: >>>
KIND: requirement
BASE_UID: A07
VERSION_N: 0
rbac_op: project:grant:create
priority: 50
iteration: iter-r0
security.catalog_ref: AC-2
security.verification_note: AC-2/AC-3/AC-6 grant administration. ASD STIG V6R4 V-222542 / V-222467 / V-222429.
edge: ← satisfies from CAP-RBAC
edge: ← refines from ARCH-CRED-REAUTH
edge: ← uses from FIX-DENY-PRIV-NO-MFA
edge: ← uses from ARCH-AUTH-CLAIM-MAP
edge: ← satisfies from CAP-RBAC.1
in_scope_of_contract: Design-2026-10
in_scope_of_contract: Security package
in_scope_of_contract: ReqALM product (build)
delivered_by_release: R0-sequences
edge: → conforms_to to AC-3 (pin imprint=nist-800-53@rev5-dogfood-20261006)
edge: → conforms_to to AC-6 (pin imprint=nist-800-53@rev5-dogfood-20261006)
edge: → conforms_to to AC-2 (pin imprint=nist-800-53@rev5-dogfood-20261006)
edge: → conforms_to to CM-5 (pin imprint=nist-800-53@rev5-dogfood-20261006)
edge: → conforms_to to V-222542 (pin imprint=asd-stig@v6r4)
edge: → conforms_to to V-222467 (pin imprint=asd-stig@v6r4)
edge: → conforms_to to V-222429 (pin imprint=asd-stig@v6r4)
<<<
RELATIONS:
- TYPE: Parent
  VALUE: SEC-IA
- TYPE: Parent
  VALUE: AC-3
  ROLE: ConformsTo
- TYPE: Parent
  VALUE: AC-6
  ROLE: ConformsTo
- TYPE: Parent
  VALUE: AC-2
  ROLE: ConformsTo
- TYPE: Parent
  VALUE: CM-5
  ROLE: ConformsTo
- TYPE: Parent
  VALUE: V-222542
  ROLE: ConformsTo
- TYPE: Parent
  VALUE: V-222467
  ROLE: ConformsTo
- TYPE: Parent
  VALUE: V-222429
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r0-sequences
  ROLE: Delivers

[REQUIREMENT]
UID: A08
STATUS: Active
TITLE: Revoke project role
STATEMENT: >>>
A project admin revokes a project role from an identity. ReqAML removes or tombstones the grant and audits
the revocation. Active sessions for the subject lose the role on the next authorization check;
desk attachments that required the role are detached.
<<<
COMMENT: >>>
KIND: requirement
BASE_UID: A08
VERSION_N: 0
rbac_op: project:grant:revoke
priority: 50
iteration: iter-r0
security.catalog_ref: AC-2
security.verification_note: AC-2/AC-3 revoke path; AU-2/3/12. ASD STIG V6R4 V-222467 / V-222407.
edge: ← satisfies from CAP-RBAC
edge: ← uses from ARCH-AUTH-UPSTREAM-REVOKE
edge: ← satisfies from CAP-RBAC.1
in_scope_of_contract: Design-2026-10
in_scope_of_contract: Security package
in_scope_of_contract: ReqALM product (build)
delivered_by_release: R0-sequences
edge: → conforms_to to AC-2 (pin imprint=nist-800-53@rev5-dogfood-20261006)
edge: → conforms_to to V-222467 (pin imprint=asd-stig@v6r4)
edge: → conforms_to to V-222407 (pin imprint=asd-stig@v6r4)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-IA
- TYPE: Parent
  VALUE: AC-2
  ROLE: ConformsTo
- TYPE: Parent
  VALUE: V-222467
  ROLE: ConformsTo
- TYPE: Parent
  VALUE: V-222407
  ROLE: ConformsTo
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r0-sequences
  ROLE: Delivers

[REQUIREMENT]
UID: A09
STATUS: Active
TITLE: Grant catalog-steward role
STATEMENT: >>>
A client or project admin grants catalog-steward at global, client, or project scope to an identity.
ReqAML records the steward grant at the requested catalog scope and audits actor, subject, and scope.
Only stewards may mutate non-standard catalog entries at their scope; standard catalogs remain read-only.
<<<
COMMENT: >>>
KIND: requirement
BASE_UID: A09
VERSION_N: 0
rbac_op: catalog:steward:grant
priority: 55
iteration: iter-r1
security.catalog_ref: AC-2
security.verification_note: AC-2 account management for steward roles; AU-2/3/12. ASD STIG V6R4 V-222407 / V-222467.
edge: ← satisfies from CAP-RBAC
edge: ← satisfies from CAP-RBAC.1
in_scope_of_contract: Design-2026-10
in_scope_of_contract: Security package
in_scope_of_contract: ReqALM product (build)
delivered_by_release: R1-core-ALM
edge: → conforms_to to AC-2 (pin imprint=nist-800-53@rev5-dogfood-20261006)
edge: → conforms_to to V-222407 (pin imprint=asd-stig@v6r4)
edge: → conforms_to to V-222467 (pin imprint=asd-stig@v6r4)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-IA
- TYPE: Parent
  VALUE: AC-2
  ROLE: ConformsTo
- TYPE: Parent
  VALUE: V-222407
  ROLE: ConformsTo
- TYPE: Parent
  VALUE: V-222467
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r1-core-alm
  ROLE: Delivers

[REQUIREMENT]
UID: A10
STATUS: Active
TITLE: Revoke catalog-steward role
STATEMENT: >>>
An admin revokes a catalog-steward grant. ReqAML tombstones the steward grant and audits the revocation.
The subject immediately loses mutate rights on catalogs at that scope; browse/reference of standards remains allowed per Reader rules.
<<<
COMMENT: >>>
KIND: requirement
BASE_UID: A10
VERSION_N: 0
rbac_op: catalog:steward:revoke
priority: 55
iteration: iter-r1
security.catalog_ref: AC-2
security.verification_note: AC-2/AC-3 steward revoke; AU-2/3/12. ASD STIG V6R4 V-222467.
edge: ← satisfies from CAP-RBAC
edge: ← satisfies from CAP-RBAC.1
in_scope_of_contract: Design-2026-10
in_scope_of_contract: Security package
in_scope_of_contract: ReqALM product (build)
delivered_by_release: R1-core-ALM
edge: → conforms_to to V-222467 (pin imprint=asd-stig@v6r4)
edge: → conforms_to to AC-2 (pin imprint=nist-800-53@rev5-dogfood-20261006)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-IA
- TYPE: Parent
  VALUE: V-222467
  ROLE: ConformsTo
- TYPE: Parent
  VALUE: AC-2
  ROLE: ConformsTo
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r1-core-alm
  ROLE: Delivers

[REQUIREMENT]
UID: A11
STATUS: Active
TITLE: List project access
STATEMENT: >>>
A project admin or auditor lists who has access to a project. ReqAML returns identity display names,
emails, and active roles filtered by the caller's permission to view grants.
The response is read-only and does not expose other projects' grant tables.
<<<
COMMENT: >>>
KIND: requirement
BASE_UID: A11
VERSION_N: 0
rbac_op: project:grant:list
priority: 45
iteration: iter-r1
security.catalog_ref: AC-3
security.verification_note: AC-3 least disclosure of grant listings; AU optional. ASD STIG V6R4 V-222430.
edge: ← satisfies from CAP-RBAC
edge: ← satisfies from CAP-RBAC.1
edge: ← satisfies from CAP-READ-ACCESS
in_scope_of_contract: Design-2026-10
in_scope_of_contract: Security package
in_scope_of_contract: ReqALM product (build)
delivered_by_release: R1-core-ALM
edge: → conforms_to to AC-6 (pin imprint=nist-800-53@rev5-dogfood-20261006)
edge: → conforms_to to V-222430 (pin imprint=asd-stig@v6r4)
edge: → conforms_to to AC-3 (pin imprint=nist-800-53@rev5-dogfood-20261006)
<<<
RELATIONS:
- TYPE: Parent
  VALUE: SEC-IA
- TYPE: Parent
  VALUE: AC-6
  ROLE: ConformsTo
- TYPE: Parent
  VALUE: V-222430
  ROLE: ConformsTo
- TYPE: Parent
  VALUE: AC-3
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r1-core-alm
  ROLE: Delivers

[REQUIREMENT]
UID: A12
STATUS: Deleted
TITLE: Impersonate / break-glass (deferred)
STATEMENT: >>>
Break-glass impersonation was considered for support scenarios. The design rejects in-product impersonation
for R0–R1; support uses IdP break-glass outside ReqAML if ever needed.
<<<
COMMENT: >>>
KIND: requirement
BASE_UID: A12
VERSION_N: 0
rbac_op: identity:impersonate
priority: 90
iteration: iter-r2
security.catalog_ref: AC-6
security.verification_note: Withdrawn: no in-product impersonation. AC-6 least privilege preserved by omission.
edge: ← refines from A12.1
edge: → conforms_to to AC-6 (pin imprint=nist-800-53@rev5-dogfood-20261006)
<<<
RELATIONS:
- TYPE: Parent
  VALUE: SEC-IA
- TYPE: Parent
  VALUE: AC-6
  ROLE: ConformsTo

[REQUIREMENT]
UID: A12.1
STATUS: Active
TITLE: Impersonate / break-glass (deferred)
STATEMENT: >>>
Impersonation / break-glass remains out of scope. This active successor documents the permanent deferral:
operators must use IdP-level emergency access; ReqAML will not mint subject-as tokens.
Audit note: any future reconsideration requires a new Security package contract review.
<<<
COMMENT: >>>
KIND: requirement
BASE_UID: A12
VERSION_N: 1
iteration: iter-r2
security.catalog_ref: AC-6
security.verification_note: Active deferral record. No rbac_op shipped. Impersonation omitted preserves least privilege (AC-6); ASD STIG V6R4 V-222429 privileged-function prevention by omission.
in_scope_of_contract: Design-2026-10
in_scope_of_contract: Security package
in_scope_of_contract: ReqALM product (build)
delivered_by_release: R1-core-ALM
edge: → conforms_to to AC-3 (pin imprint=nist-800-53@rev5-dogfood-20261006)
edge: → conforms_to to V-222429 (pin imprint=asd-stig@v6r4)
edge: → conforms_to to AC-6 (pin imprint=nist-800-53@rev5-dogfood-20261006)
<<<
RELATIONS:
- TYPE: Parent
  VALUE: SEC-IA
- TYPE: Parent
  VALUE: AC-3
  ROLE: ConformsTo
- TYPE: Parent
  VALUE: A12
  ROLE: Refines
- TYPE: Parent
  VALUE: V-222429
  ROLE: ConformsTo
- TYPE: Parent
  VALUE: AC-6
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r1-core-alm
  ROLE: Delivers

[REQUIREMENT]
UID: CAP-RBAC
STATUS: Draft
TITLE: RBAC enforcement on API mutations
STATEMENT: >>>
API routes enforce project-grant derived permissions (CAP-RBAC matrix subset). `POST /api/v1/projects/:projectId/grants` requires `grant:manage`; Readers receive 403 with audit. MCP `/mcp` requires MCP-audience tokens. Acceptance: auth-flow-smoke RBAC deny for casey-reader.
<<<
COMMENT: >>>
KIND: capability
BASE_UID: CAP-RBAC
VERSION_N: 0
priority: 10
iteration: iter-r1
security.catalog_ref: AC-3
security.verification_note: AC-3 enforcement. Verified: Local Docker 2026-10-07 on PR #13 follow-up (6a5f0db + verification fixes), fresh volumes: `pnpm devenv:init` idempotent (byte-identical rerun), `--rotate` issues new secrets (needs `down -v` for the Postgres volume), secrets files mode 600 and gitignored; `docker compose up --build -d --wait` with and without the hostports overlay (app 127.0.0.1:3000 only; peripherals unpublished without the overlay, loopback-only with it); /ready all green, restart count 0; `pnpm devenv:smoke` pass incl. auth-flow-smoke (server-side OAuth handoffs, PKCE S256, refresh rotation/reuse family revoke, RFC7009 refresh+access revoke, lockout + username normalize, Reader RBAC 403, wrong audience 401 at MCP, upstream connectors 401 unauthenticated, session cookie HttpOnly+SameSite=Lax, cookie mutation without CSRF 401, signout ends session, sam-security MFA login via `devenv:mfa`, TOTP replay rejected (and one wrong code does not lock the account), agent tokens default Reader / Author max / Developer+ refused, TTL <= 1h, agent token revoked 401), auth_audit_events incl. agent-attributed mutation, IP throttle 200 -> 401 after 20 failures, production refused dev accounts/keys, missing REQALM_ISSUER_URL and blanket trustProxy; headless Chrome first-login TOTP enrollment (jamie-ao) then MFA re-login; `@reqalm/app` test 30/30, typecheck pass; seed yaml_to_strictdoc --validate pass.
edge: ← uses from MC03
edge: ← uses from FIX-DENY-READER-GRANT
edge: ← uses from FIX-DENY-MCP-ESCALATE
edge: ← uses from FIX-DENY-NO-GRANT
edge: ← uses from FIX-DENY-REVOKED
edge: ← satisfies from CAP-SVC-OPERATION-EXECUTOR
edge: ← satisfies from CAP-READ-REQS
edge: ← satisfies from CAP-READ-RELEASES
edge: ← satisfies from CAP-READ-HIERARCHY
edge: ← refines from CAP-RBAC.1
edge: ← satisfies from CAP-SVC-OPERATION-EXECUTOR.1
edge: ← satisfies from CAP-SVC-RBAC-NO-PROJECT
edge: ← satisfies from CAP-READ-ACCESS
in_scope_of_contract: Design-2026-10
in_scope_of_contract: Security package
in_scope_of_contract: Platform baseline
delivered_by_release: R0-sequences
delivered_by_release: R1 — foundation shell + internal auth
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-IA
- TYPE: Parent
  VALUE: A05
  ROLE: Satisfies
- TYPE: Parent
  VALUE: A06
  ROLE: Satisfies
- TYPE: Parent
  VALUE: A07
  ROLE: Satisfies
- TYPE: Parent
  VALUE: A08
  ROLE: Satisfies
- TYPE: Parent
  VALUE: A09
  ROLE: Satisfies
- TYPE: Parent
  VALUE: A10
  ROLE: Satisfies
- TYPE: Parent
  VALUE: A11
  ROLE: Satisfies
- TYPE: Parent
  VALUE: ARCH-API-RBAC
  ROLE: Satisfies
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-security-package
  ROLE: InScopeOf
- TYPE: Child
  VALUE: CONTRACT-contract-platform-baseline
  ROLE: InScopeOf
- TYPE: Child
  VALUE: RELEASE-rel-r0-sequences
  ROLE: Delivers
- TYPE: Child
  VALUE: RELEASE-rel-r1-foundation-shell-auth
  ROLE: Delivers

[REQUIREMENT]
UID: CAP-RBAC.1
STATUS: Active
TITLE: RBAC enforcement on API mutations
STATEMENT: >>>
Capability pack for API RBAC enforcement (subset of the full permission matrix). Shipped foundation covers OAuth routes, defineOperationRoute business reads, and auth-flow-smoke beds — not every ARCH-API-RBAC mutating operation. MCP and grant-management mutators remain planned in core-ALM.
<<<
COMMENT: >>>
KIND: capability
BASE_UID: CAP-RBAC
VERSION_N: 1
priority: 10
iteration: iter-r1
security.catalog_ref: AC-3
security.verification_note: Partial pass on .1: foundation + read routes verified; full matrix deferred to core-ALM. Verified: Local Docker 2026-10-07 on PR #13 follow-up (6a5f0db + verification fixes).
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-IA
- TYPE: Parent
  VALUE: CAP-RBAC
  ROLE: Refines
- TYPE: Parent
  VALUE: A05
  ROLE: Satisfies
- TYPE: Parent
  VALUE: A06
  ROLE: Satisfies
- TYPE: Parent
  VALUE: A07
  ROLE: Satisfies
- TYPE: Parent
  VALUE: A08
  ROLE: Satisfies
- TYPE: Parent
  VALUE: A09
  ROLE: Satisfies
- TYPE: Parent
  VALUE: A10
  ROLE: Satisfies
- TYPE: Parent
  VALUE: A11
  ROLE: Satisfies
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Parent
  VALUE: ARCH-API-RBAC.1
  ROLE: Satisfies
- TYPE: Child
  VALUE: CONTRACT-ctr-reqalm-product
  ROLE: InScopeOf

[REQUIREMENT]
UID: ARCH-AUTH-AS
STATUS: Active
TITLE: Internal OAuth 2.1 authorization server (single token issuer)
STATEMENT: >>>
ReqAML includes its own OAuth 2.1 authorization server (AS) and it is the single token issuer for the Web UI, API, and MCP clients. It runs in the app container's API role. Only the authorization code grant with PKCE is supported for user-delegated access (no implicit, no resource-owner password grant). The AS conforms to the MCP authorization specification (OAuth 2.1, RFC 8414, RFC 9728, RFC 8707, RFC 9207 iss). Users authenticate at the AS either with a local account (ARCH-AUTH-LOCAL) or through a federated enterprise IdP (ARCH-AUTH-FEDERATION); either way the API and MCP server only accept tokens issued by this AS. Signing uses KeyProvider keys (ARCH-KEY-JWKS), and every auth event is audited (ARCH-CRED-AUDIT).
<<<
COMMENT: >>>
KIND: requirement
BASE_UID: ARCH-AUTH-AS
VERSION_N: 0
rbac_op: auth:oauth:authorize, auth:oauth:token
priority: 5
iteration: iter-r1
security.catalog_ref: IA-2
security.verification_note: IA-2/IA-5/IA-8/SC-23; single issuer for UI, API, MCP. ASD V-222522.
edge: ← refines from ARCH-AUTH-PKCE
edge: ← refines from ARCH-AUTH-METADATA
edge: ← refines from ARCH-AUTH-AUDIENCE
edge: ← refines from ARCH-AUTH-REFRESH
edge: ← refines from ARCH-AUTH-REVOKE
edge: ← refines from ARCH-AUTH-CLIENTREG
edge: ← refines from ARCH-AUTH-FEDERATION
edge: ← refines from ARCH-AUTH-LOCAL
edge: ← uses from ARCH-DEVENV-COMPOSE.1
edge: ← uses from ARCH-DEVENV-IDENTITY.1
edge: ← uses from ARCH-BUILD-FOUNDATION
edge: ← refines from ARCH-AUTH-LOCAL.1
edge: ← refines from ARCH-AUTH-PROFILE
edge: ← refines from ARCH-AUTH-MCP-REQUIRED
edge: ← satisfies from CAP-OAUTH-AS
edge: ← satisfies from CAP-AUTH-HARDEN
edge: ← satisfies from CAP-AUTH-HARDEN.1
in_scope_of_contract: ReqALM product (build)
delivered_by_release: R1 — foundation shell + internal auth
edge: → conforms_to to IA-2 (pin imprint=nist-800-53@rev5-dogfood-20261006)
edge: → conforms_to to IA-5 (pin imprint=nist-800-53@rev5-dogfood-20261006)
edge: → conforms_to to IA-8 (pin imprint=nist-800-53@rev5-dogfood-20261006)
edge: → conforms_to to SC-23 (pin imprint=nist-800-53@rev5-dogfood-20261006)
edge: → conforms_to to V-222522 (pin imprint=asd-stig@v6r4)
<<<
RELATIONS:
- TYPE: Parent
  VALUE: SEC-IA
- TYPE: Parent
  VALUE: A01
  ROLE: Refines
- TYPE: Parent
  VALUE: MC01.1
  ROLE: Refines
- TYPE: Parent
  VALUE: ARCH-API
  ROLE: Uses
- TYPE: Parent
  VALUE: ARCH-KEY-JWKS
  ROLE: Uses
- TYPE: Parent
  VALUE: ARCH-CRED-AUDIT
  ROLE: Uses
- TYPE: Parent
  VALUE: ARCH-DEPLOY-MINIMAL
  ROLE: Uses
- TYPE: Parent
  VALUE: IA-2
  ROLE: ConformsTo
- TYPE: Parent
  VALUE: IA-5
  ROLE: ConformsTo
- TYPE: Parent
  VALUE: IA-8
  ROLE: ConformsTo
- TYPE: Parent
  VALUE: SC-23
  ROLE: ConformsTo
- TYPE: Parent
  VALUE: V-222522
  ROLE: ConformsTo
- TYPE: Child
  VALUE: CONTRACT-ctr-reqalm-product
  ROLE: InScopeOf
- TYPE: Child
  VALUE: RELEASE-rel-r1-foundation-shell-auth
  ROLE: Delivers

[[SECTION]]
UID: ARCH-AUTH-AS-CHILDREN
TITLE: Children of ARCH-AUTH-AS

[REQUIREMENT]
UID: ARCH-AUTH-PKCE
STATUS: Active
TITLE: Authorization code + PKCE S256 only
STATEMENT: >>>
The authorization endpoint requires PKCE with code_challenge_method=S256. Requests that use plain or omit the challenge are rejected (invalid_request) and no code is issued. AS metadata advertises code_challenge_methods_supported=["S256"]. Authorization codes are single-use and short-lived, bound to client_id, redirect_uri (exact match), and code_challenge. State is required, and the authorization response carries iss (RFC 9207).
<<<
COMMENT: >>>
KIND: requirement
BASE_UID: ARCH-AUTH-PKCE
VERSION_N: 0
rbac_op: auth:oauth:authorize
priority: 5
iteration: iter-r1
security.catalog_ref: IA-2.8
security.verification_note: Replay-resistant authentication (IA-2(8)); ASD V-222530 / V-222531.
edge: ← uses from FIX-ALLOW-MCP-OAUTH-PKCE
edge: ← uses from FIX-DENY-PKCE-PLAIN
edge: ← satisfies from CAP-OAUTH-AS
edge: ← satisfies from CAP-TEST-AUTH-ROUTES
in_scope_of_contract: ReqALM product (build)
delivered_by_release: R1 — foundation shell + internal auth
edge: → conforms_to to IA-2.8 (pin imprint=nist-800-53@rev5-dogfood-20261006)
edge: → conforms_to to V-222530 (pin imprint=asd-stig@v6r4)
edge: → conforms_to to V-222531 (pin imprint=asd-stig@v6r4)
<<<
RELATIONS:
- TYPE: Parent
  VALUE: ARCH-AUTH-AS
- TYPE: Parent
  VALUE: ARCH-AUTH-AS
  ROLE: Refines
- TYPE: Parent
  VALUE: IA-2.8
  ROLE: ConformsTo
- TYPE: Parent
  VALUE: V-222530
  ROLE: ConformsTo
- TYPE: Parent
  VALUE: V-222531
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-AUTH-METADATA
STATUS: Active
TITLE: AS metadata (RFC 8414) + protected resource metadata (RFC 9728)
STATEMENT: >>>
The AS publishes Authorization Server Metadata (RFC 8414) at /.well-known/oauth-authorization-server, plus OpenID Connect discovery for interop. The metadata issuer is identical to the issuer URL. The MCP server and the API each publish OAuth Protected Resource Metadata (RFC 9728) at /.well-known/oauth-protected-resource, listing the internal AS in authorization_servers and stating their canonical resource URI. A request without a valid token gets 401 with WWW-Authenticate: Bearer resource_metadata="…" so MCP clients can discover the AS.
<<<
COMMENT: >>>
KIND: requirement
BASE_UID: ARCH-AUTH-METADATA
VERSION_N: 0
priority: 5
iteration: iter-r1
security.catalog_ref: REQALM-SEC-OAUTH
security.verification_note: MCP authorization spec discovery (RFC 8414 / RFC 9728). Interop requirement; no direct NIST pin.
edge: ← uses from FIX-ALLOW-MCP-OAUTH-PKCE
edge: ← uses from FIX-DENY-MCP-WRONG-AUDIENCE
edge: ← satisfies from CAP-OAUTH-AS
in_scope_of_contract: ReqALM product (build)
delivered_by_release: R1 — foundation shell + internal auth
edge: → conforms_to to SC-23 (pin imprint=nist-800-53@rev5-dogfood-20261006)
<<<
RELATIONS:
- TYPE: Parent
  VALUE: ARCH-AUTH-AS
- TYPE: Parent
  VALUE: ARCH-AUTH-AS
  ROLE: Refines
- TYPE: Parent
  VALUE: MC01.1
  ROLE: Refines
- TYPE: Parent
  VALUE: SC-23
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-AUTH-AUDIENCE
STATUS: Active
TITLE: Audience-bound tokens via resource indicators (RFC 8707); no passthrough
STATEMENT: >>>
Clients send the RFC 8707 resource parameter on both authorization and token requests. Access tokens are audience-bound to exactly one canonical resource (the API or the MCP server). Each resource server rejects tokens whose audience is not its own (401 invalid_token). The MCP server never passes the token it received through to the API. Downstream API calls use a separately issued API-audience token for the same subject; that mechanism is an open question. RBAC (ARCH-API-RBAC / MC03) still decides every operation after the audience check.
<<<
COMMENT: >>>
KIND: requirement
BASE_UID: ARCH-AUTH-AUDIENCE
VERSION_N: 0
rbac_op: auth:token:validate
priority: 5
iteration: iter-r1
security.catalog_ref: SC-23
security.verification_note: SC-23 session authenticity; AC-3 enforcement at each resource server.
edge: ← uses from FIX-ALLOW-MCP-OAUTH-PKCE
edge: ← uses from FIX-DENY-MCP-WRONG-AUDIENCE
edge: ← uses from ARCH-AUTH-MCP-REQUIRED
edge: ← satisfies from CAP-OAUTH-AS
edge: ← satisfies from CAP-TEST-AUTH-HYGIENE
in_scope_of_contract: ReqALM product (build)
delivered_by_release: R1 — foundation shell + internal auth
edge: → conforms_to to AC-3 (pin imprint=nist-800-53@rev5-dogfood-20261006)
edge: → conforms_to to SC-23 (pin imprint=nist-800-53@rev5-dogfood-20261006)
<<<
RELATIONS:
- TYPE: Parent
  VALUE: ARCH-AUTH-AS
- TYPE: Parent
  VALUE: ARCH-AUTH-AS
  ROLE: Refines
- TYPE: Parent
  VALUE: MC03
  ROLE: Refines
- TYPE: Parent
  VALUE: ARCH-API-RBAC
  ROLE: Uses
- TYPE: Parent
  VALUE: AC-3
  ROLE: ConformsTo
- TYPE: Parent
  VALUE: SC-23
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-AUTH-REFRESH
STATUS: Active
TITLE: Refresh token rotation with reuse detection
STATEMENT: >>>
Refresh tokens rotate on every use: the AS issues a new refresh token, invalidates the old one, and keeps them in one token family. Presenting an already-rotated refresh token is treated as theft: the AS returns invalid_grant, revokes the whole family (and derived access tokens where introspectable), and emits an audit event. Refresh tokens are bound to client_id and resource, stored hashed server-side (ARCH-CRED-TOKENS), and their idle and absolute lifetimes are configurable.
<<<
COMMENT: >>>
KIND: requirement
BASE_UID: ARCH-AUTH-REFRESH
VERSION_N: 0
rbac_op: auth:oauth:token
priority: 5
iteration: iter-r1
security.catalog_ref: SC-23
security.verification_note: SC-23 / IA-5 authenticator protection; replay-resistant refresh.
edge: ← uses from FIX-DENY-REFRESH-REUSE
edge: ← satisfies from CAP-OAUTH-AS
edge: ← satisfies from CAP-TEST-AUTH-ROUTES
in_scope_of_contract: ReqALM product (build)
delivered_by_release: R1 — foundation shell + internal auth
edge: → conforms_to to SC-23 (pin imprint=nist-800-53@rev5-dogfood-20261006)
edge: → conforms_to to IA-5 (pin imprint=nist-800-53@rev5-dogfood-20261006)
<<<
RELATIONS:
- TYPE: Parent
  VALUE: ARCH-AUTH-AS
- TYPE: Parent
  VALUE: ARCH-AUTH-AS
  ROLE: Refines
- TYPE: Parent
  VALUE: ARCH-CRED-TOKENS
  ROLE: Uses
- TYPE: Parent
  VALUE: SC-23
  ROLE: ConformsTo
- TYPE: Parent
  VALUE: IA-5
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-AUTH-REVOKE
STATUS: Active
TITLE: Token revocation and session-linked teardown
STATEMENT: >>>
The AS exposes token revocation (RFC 7009) for refresh and access tokens. Sign-out (A02) revokes the session's refresh tokens and desk attachments. Disabling or deleting an account, or revoking a grant that removes all access, terminates that subject's sessions and token families. Resource servers reject revoked tokens through introspection or short access-token lifetimes plus revocation checks.
<<<
COMMENT: >>>
KIND: requirement
BASE_UID: ARCH-AUTH-REVOKE
VERSION_N: 0
rbac_op: auth:oauth:revoke, auth:signout
priority: 10
iteration: iter-r1
security.catalog_ref: AC-12
security.verification_note: AC-12 session termination; ASD V-222549 / V-222578 / V-222391.
edge: ← uses from FIX-DENY-REVOKED-TOKEN
edge: ← refines from ARCH-AUTH-UPSTREAM-REVOKE
edge: ← satisfies from CAP-OAUTH-AS
edge: ← satisfies from CAP-TEST-AUTH-HYGIENE
in_scope_of_contract: ReqALM product (build)
delivered_by_release: R1 — foundation shell + internal auth
edge: → conforms_to to AC-12 (pin imprint=nist-800-53@rev5-dogfood-20261006)
edge: → conforms_to to V-222549 (pin imprint=asd-stig@v6r4)
edge: → conforms_to to V-222578 (pin imprint=asd-stig@v6r4)
edge: → conforms_to to V-222391 (pin imprint=asd-stig@v6r4)
<<<
RELATIONS:
- TYPE: Parent
  VALUE: ARCH-AUTH-AS
- TYPE: Parent
  VALUE: ARCH-AUTH-AS
  ROLE: Refines
- TYPE: Parent
  VALUE: A02
  ROLE: Refines
- TYPE: Parent
  VALUE: AC-12
  ROLE: ConformsTo
- TYPE: Parent
  VALUE: V-222549
  ROLE: ConformsTo
- TYPE: Parent
  VALUE: V-222578
  ROLE: ConformsTo
- TYPE: Parent
  VALUE: V-222391
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-AUTH-CLIENTREG
STATUS: Active
TITLE: Client registration: pre-registered baseline; CIMD/DCR policy-gated
STATEMENT: >>>
First-party clients (Web UI, admin-configured ReqAML MCP clients) are pre-registered with exact redirect URIs. Client ID Metadata Documents and Dynamic Client Registration (RFC 7591; deprecated in the MCP 2026-07-28 revision) ship disabled by default. An admin can enable either one per deployment or per client policy, and every registration is audited. When DCR is disabled, registration_endpoint is omitted from AS metadata and registration requests are refused. Confidential-client secrets are stored hashed (ARCH-CRED-TOKENS).
<<<
COMMENT: >>>
KIND: requirement
BASE_UID: ARCH-AUTH-CLIENTREG
VERSION_N: 0
rbac_op: auth:client:register
priority: 15
iteration: iter-r1
security.catalog_ref: CM-7
security.verification_note: CM-7 least functionality: open registration off unless policy enables it.
edge: ← uses from FIX-DENY-DCR-DISABLED
edge: ← satisfies from CAP-OAUTH-AS
in_scope_of_contract: ReqALM product (build)
delivered_by_release: R1 — foundation shell + internal auth
edge: → conforms_to to CM-7 (pin imprint=nist-800-53@rev5-dogfood-20261006)
edge: → conforms_to to AU-2 (pin imprint=nist-800-53@rev5-dogfood-20261006)
<<<
RELATIONS:
- TYPE: Parent
  VALUE: ARCH-AUTH-AS
- TYPE: Parent
  VALUE: ARCH-AUTH-AS
  ROLE: Refines
- TYPE: Parent
  VALUE: ARCH-CRED-TOKENS
  ROLE: Uses
- TYPE: Parent
  VALUE: CM-7
  ROLE: ConformsTo
- TYPE: Parent
  VALUE: AU-2
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-AUTH-FEDERATION
STATUS: Active
TITLE: Enterprise SSO federated upstream through the internal AS
STATEMENT: >>>
The enterprise IdP (OIDC or SAML), formerly the direct sign-in path in A01 / CAP-SSO / REQAML-SEC-SSO, is an upstream identity provider federated through the internal AS, not a separate token path. The AS acts as the OIDC RP / SAML SP. It validates the upstream response (signature, issuer, audience, nonce, NotBefore/NotOnOrAfter, single-use assertion ID), maps external_sub to a linked identity (A06), and then issues ReqAML tokens through the normal code + PKCE flow. When the role needs MFA (ARCH-CRED-MFA), the AS requires upstream MFA evidence (amr/acr). The API and MCP server never accept upstream IdP tokens directly.
<<<
COMMENT: >>>
KIND: requirement
BASE_UID: ARCH-AUTH-FEDERATION
VERSION_N: 0
rbac_op: auth:signin
priority: 5
iteration: iter-r1
security.catalog_ref: IA-2
security.verification_note: IA-2 / IA-8 federated identification; ASD V-222400 / V-222401 / V-222403 / V-222404 SAML assertion checks.
edge: ← uses from FIX-DENY-UPSTREAM-TOKEN-AT-API
edge: ← uses from FIX-ALLOW-FEDERATED-SSO-VIA-AS
edge: ← refines from ARCH-AUTH-UPSTREAM-CONNECTOR
edge: ← refines from ARCH-AUTH-CLAIM-MAP
edge: ← refines from ARCH-AUTH-UPSTREAM-REVOKE
edge: ← uses from FIX-ALLOW-MCP-OAUTH-FEDERATED-ONLY
in_scope_of_contract: ReqALM product (build)
delivered_by_release: R1 platform follow-ups (deferred from foundation PR)
edge: → conforms_to to IA-2 (pin imprint=nist-800-53@rev5-dogfood-20261006)
edge: → conforms_to to IA-8 (pin imprint=nist-800-53@rev5-dogfood-20261006)
edge: → conforms_to to V-222400 (pin imprint=asd-stig@v6r4)
edge: → conforms_to to V-222401 (pin imprint=asd-stig@v6r4)
edge: → conforms_to to V-222403 (pin imprint=asd-stig@v6r4)
edge: → conforms_to to V-222404 (pin imprint=asd-stig@v6r4)
edge: → conforms_to to V-222522 (pin imprint=asd-stig@v6r4)
<<<
RELATIONS:
- TYPE: Parent
  VALUE: ARCH-AUTH-AS
- TYPE: Parent
  VALUE: ARCH-AUTH-AS
  ROLE: Refines
- TYPE: Parent
  VALUE: A01
  ROLE: Refines
- TYPE: Parent
  VALUE: CAP-SSO
  ROLE: Refines
- TYPE: Parent
  VALUE: A06
  ROLE: Uses
- TYPE: Parent
  VALUE: ARCH-CRED-MFA
  ROLE: Uses
- TYPE: Parent
  VALUE: IA-2
  ROLE: ConformsTo
- TYPE: Parent
  VALUE: IA-8
  ROLE: ConformsTo
- TYPE: Parent
  VALUE: V-222400
  ROLE: ConformsTo
- TYPE: Parent
  VALUE: V-222401
  ROLE: ConformsTo
- TYPE: Parent
  VALUE: V-222403
  ROLE: ConformsTo
- TYPE: Parent
  VALUE: V-222404
  ROLE: ConformsTo
- TYPE: Parent
  VALUE: V-222522
  ROLE: ConformsTo
- TYPE: Child
  VALUE: CONTRACT-ctr-reqalm-product
  ROLE: InScopeOf
- TYPE: Child
  VALUE: RELEASE-rel-r1-platform-followups
  ROLE: Delivers

[[SECTION]]
UID: ARCH-AUTH-FEDERATION-CHILDREN
TITLE: Children of ARCH-AUTH-FEDERATION

[REQUIREMENT]
UID: ARCH-AUTH-UPSTREAM-CONNECTOR
STATUS: Active
TITLE: Pluggable upstream IdP connector per client tenant
STATEMENT: >>>
Upstream identity providers attach through a pluggable connector interface (built in: OIDC RP and SAML 2.0 SP; other protocols through additional connectors). Each connector is registered to exactly one client tenant (client_id). Its client secrets and signing or decryption keys are stored under the key store (ARCH-KEY-SCOPE). A connector's assertions can only establish sessions for identities linked within that tenant (A06): a subject from client A's connector never obtains grants in client B, and cross-tenant access goes through ReqAML grants, not the connector. Connector configuration is managed by Client admin, needs step-up (ARCH-CRED-REAUTH), and is audited. How many connectors a tenant may have, how one is selected (home-realm discovery), and which non-OIDC/SAML protocols are supported are open questions (docs/design/auth/mcp-upstream-identity.md).
<<<
COMMENT: >>>
KIND: requirement
BASE_UID: ARCH-AUTH-UPSTREAM-CONNECTOR
VERSION_N: 0
rbac_op: auth:connector:configure
priority: 10
iteration: iter-r1
security.catalog_ref: IA-8
security.verification_note: IA-8 non-organizational users / federation; AC-3 tenant isolation; ASD V-222559 / V-222560.
edge: ← uses from ARCH-AUTH-CLAIM-MAP
edge: ← uses from FIX-DENY-CROSS-TENANT-CONNECTOR
edge: ← satisfies from CAP-AUTH-UPSTREAM-SEAM
in_scope_of_contract: ReqALM product (build)
delivered_by_release: R1 — foundation shell + internal auth
edge: → conforms_to to IA-8 (pin imprint=nist-800-53@rev5-dogfood-20261006)
edge: → conforms_to to IA-2 (pin imprint=nist-800-53@rev5-dogfood-20261006)
edge: → conforms_to to AC-3 (pin imprint=nist-800-53@rev5-dogfood-20261006)
edge: → conforms_to to V-222400 (pin imprint=asd-stig@v6r4)
edge: → conforms_to to V-222401 (pin imprint=asd-stig@v6r4)
edge: → conforms_to to V-222403 (pin imprint=asd-stig@v6r4)
edge: → conforms_to to V-222404 (pin imprint=asd-stig@v6r4)
edge: → conforms_to to V-222559 (pin imprint=asd-stig@v6r4)
edge: → conforms_to to V-222560 (pin imprint=asd-stig@v6r4)
<<<
RELATIONS:
- TYPE: Parent
  VALUE: ARCH-AUTH-FEDERATION
- TYPE: Parent
  VALUE: ARCH-AUTH-FEDERATION
  ROLE: Refines
- TYPE: Parent
  VALUE: ARCH-CP-SCOPE
  ROLE: Uses
- TYPE: Parent
  VALUE: ARCH-KEY-SCOPE
  ROLE: Uses
- TYPE: Parent
  VALUE: A06
  ROLE: Uses
- TYPE: Parent
  VALUE: ARCH-CRED-REAUTH
  ROLE: Uses
- TYPE: Parent
  VALUE: IA-8
  ROLE: ConformsTo
- TYPE: Parent
  VALUE: IA-2
  ROLE: ConformsTo
- TYPE: Parent
  VALUE: AC-3
  ROLE: ConformsTo
- TYPE: Parent
  VALUE: V-222400
  ROLE: ConformsTo
- TYPE: Parent
  VALUE: V-222401
  ROLE: ConformsTo
- TYPE: Parent
  VALUE: V-222403
  ROLE: ConformsTo
- TYPE: Parent
  VALUE: V-222404
  ROLE: ConformsTo
- TYPE: Parent
  VALUE: V-222559
  ROLE: ConformsTo
- TYPE: Parent
  VALUE: V-222560
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-AUTH-CLAIM-MAP
STATUS: Active
TITLE: Upstream claim-to-identity/grant mapping is explicit, tenant-bounded config
STATEMENT: >>>
Mapping from upstream claims or attributes (sub/NameID, email, groups, amr/acr) to ReqAML identity, and optionally to grants, is explicit per-connector configuration. It is versioned, step-up gated, and audited, and is never implicit trust in upstream attributes. The identity key is the upstream issuer plus subject, never email alone. A mapping can never grant beyond its connector's tenant and never grants deployment-scoped roles (for example, Key custodian). Whether upstream groups may provision or deprovision ReqAML grants automatically is an open question. Until it is decided, grants come only from ReqAML grant records (A07 / A08), and upstream claims establish identity and MFA evidence only.
<<<
COMMENT: >>>
KIND: requirement
BASE_UID: ARCH-AUTH-CLAIM-MAP
VERSION_N: 0
rbac_op: auth:connector:configure
priority: 10
iteration: iter-r1
security.catalog_ref: AC-2
security.verification_note: AC-2 account management; AC-6 least privilege; AU-2.
in_scope_of_contract: ReqALM product (build)
delivered_by_release: R1 platform follow-ups (deferred from foundation PR)
edge: → conforms_to to AC-2 (pin imprint=nist-800-53@rev5-dogfood-20261006)
edge: → conforms_to to AC-6 (pin imprint=nist-800-53@rev5-dogfood-20261006)
edge: → conforms_to to AU-2 (pin imprint=nist-800-53@rev5-dogfood-20261006)
<<<
RELATIONS:
- TYPE: Parent
  VALUE: ARCH-AUTH-FEDERATION
- TYPE: Parent
  VALUE: ARCH-AUTH-FEDERATION
  ROLE: Refines
- TYPE: Parent
  VALUE: ARCH-AUTH-UPSTREAM-CONNECTOR
  ROLE: Uses
- TYPE: Parent
  VALUE: A06
  ROLE: Uses
- TYPE: Parent
  VALUE: A07
  ROLE: Uses
- TYPE: Parent
  VALUE: ARCH-API-RBAC
  ROLE: Uses
- TYPE: Parent
  VALUE: AC-2
  ROLE: ConformsTo
- TYPE: Parent
  VALUE: AC-6
  ROLE: ConformsTo
- TYPE: Parent
  VALUE: AU-2
  ROLE: ConformsTo
- TYPE: Child
  VALUE: CONTRACT-ctr-reqalm-product
  ROLE: InScopeOf
- TYPE: Child
  VALUE: RELEASE-rel-r1-platform-followups
  ROLE: Delivers

[REQUIREMENT]
UID: ARCH-AUTH-UPSTREAM-REVOKE
STATUS: Active
TITLE: Upstream session end and revocation are honored
STATEMENT: >>>
Upstream session end and revocation are honored. On an upstream back-channel logout (OIDC Back-Channel Logout or SAML SLO) where the connector supports it, the AS ends the linked ReqAML sessions and revokes their token families, including MCP refresh tokens. Each connector sets a maximum upstream authentication age; ReqAML refresh and session lifetimes never extend access past it without upstream re-authentication. An identity disabled or unlinked in ReqAML (A06 / A08) loses all sessions and tokens immediately. Revocation-propagation events are audited. Handling for IdPs without back-channel logout (polling, SCIM deprovisioning) is an open question, bounded meanwhile by the maximum authentication age.
<<<
COMMENT: >>>
KIND: requirement
BASE_UID: ARCH-AUTH-UPSTREAM-REVOKE
VERSION_N: 0
rbac_op: auth:oauth:revoke
priority: 10
iteration: iter-r1
security.catalog_ref: AC-12
security.verification_note: AC-12 session termination; AC-2(3); ASD V-222549 / V-222391.
edge: ← uses from FIX-DENY-UPSTREAM-LOGOUT-PROPAGATED
in_scope_of_contract: ReqALM product (build)
delivered_by_release: R1 platform follow-ups (deferred from foundation PR)
edge: → conforms_to to AC-12 (pin imprint=nist-800-53@rev5-dogfood-20261006)
edge: → conforms_to to AC-2.3 (pin imprint=nist-800-53@rev5-dogfood-20261006)
edge: → conforms_to to SC-23 (pin imprint=nist-800-53@rev5-dogfood-20261006)
edge: → conforms_to to V-222549 (pin imprint=asd-stig@v6r4)
edge: → conforms_to to V-222391 (pin imprint=asd-stig@v6r4)
<<<
RELATIONS:
- TYPE: Parent
  VALUE: ARCH-AUTH-FEDERATION
- TYPE: Parent
  VALUE: ARCH-AUTH-FEDERATION
  ROLE: Refines
- TYPE: Parent
  VALUE: ARCH-AUTH-REVOKE
  ROLE: Refines
- TYPE: Parent
  VALUE: ARCH-CRED-SESSION
  ROLE: Uses
- TYPE: Parent
  VALUE: A08
  ROLE: Uses
- TYPE: Parent
  VALUE: AC-12
  ROLE: ConformsTo
- TYPE: Parent
  VALUE: AC-2.3
  ROLE: ConformsTo
- TYPE: Parent
  VALUE: SC-23
  ROLE: ConformsTo
- TYPE: Parent
  VALUE: V-222549
  ROLE: ConformsTo
- TYPE: Parent
  VALUE: V-222391
  ROLE: ConformsTo
- TYPE: Child
  VALUE: CONTRACT-ctr-reqalm-product
  ROLE: InScopeOf
- TYPE: Child
  VALUE: RELEASE-rel-r1-platform-followups
  ROLE: Delivers

[[/SECTION]]

[REQUIREMENT]
UID: ARCH-AUTH-LOCAL
STATUS: Draft
TITLE: Local accounts: optional per auth profile (off by default in production)
STATEMENT: >>>
The internal identity store supports local accounts that bind to the same identity rows and grants as federated identities. Local accounts are required for development (seeded dev accounts, ARCH-DEVENV-IDENTITY.1) and available to deployments whose policy enables them; production enablement and eligible users are an open question. Every local credential is subject to ARCH-CRED-*. Account create/modify/disable/remove is automated and audited, and unnecessary or built-in accounts are disabled.
<<<
COMMENT: >>>
KIND: requirement
BASE_UID: ARCH-AUTH-LOCAL
VERSION_N: 0
rbac_op: auth:local:signin, identity:account:manage
priority: 10
iteration: iter-r1
security.catalog_ref: AC-2
security.verification_note: AC-2 account management; ASD V-222407 / V-222412 / V-222661.
edge: ← refines from ARCH-AUTH-LOCAL.1
edge: → conforms_to to AC-2 (pin imprint=nist-800-53@rev5-dogfood-20261006)
edge: → conforms_to to IA-2 (pin imprint=nist-800-53@rev5-dogfood-20261006)
edge: → conforms_to to V-222407 (pin imprint=asd-stig@v6r4)
edge: → conforms_to to V-222412 (pin imprint=asd-stig@v6r4)
edge: → conforms_to to V-222661 (pin imprint=asd-stig@v6r4)
<<<
RELATIONS:
- TYPE: Parent
  VALUE: ARCH-AUTH-AS
- TYPE: Parent
  VALUE: ARCH-AUTH-AS
  ROLE: Refines
- TYPE: Parent
  VALUE: ARCH-CRED
  ROLE: Uses
- TYPE: Parent
  VALUE: AC-2
  ROLE: ConformsTo
- TYPE: Parent
  VALUE: IA-2
  ROLE: ConformsTo
- TYPE: Parent
  VALUE: V-222407
  ROLE: ConformsTo
- TYPE: Parent
  VALUE: V-222412
  ROLE: ConformsTo
- TYPE: Parent
  VALUE: V-222661
  ROLE: ConformsTo

[REQUIREMENT]
UID: ARCH-AUTH-LOCAL.1
STATUS: Active
TITLE: Local accounts: optional per auth profile (off by default in production)
STATEMENT: >>>
Local password accounts are an optional capability of the auth profile (ARCH-AUTH-PROFILE), not a baseline. The setting local_accounts takes one of three values: disabled (default for every production profile), breakglass_only (only ARCH-AUTH-LOCAL-BREAKGLASS accounts), or enabled (a profile that explicitly opts in). The development profile uses enabled with seeded dev accounts (ARCH-DEVENV-IDENTITY.1). With disabled: no local credential records exist, the local login route and form are absent, and sign-in is federated only. This keeps A01 / CAP-SSO / REQAML-SEC-SSO ('no local password store; MFA at the IdP') as the default production posture, so A01 is not minted. Where local accounts are enabled, they bind to the same identity rows and grants as federated identities, every local credential is subject to ARCH-CRED-*, account lifecycle is automated and audited, and unnecessary or built-in accounts are disabled. The internal AS and OAuth for MCP are required whatever this setting is (ARCH-AUTH-MCP-REQUIRED).
<<<
COMMENT: >>>
KIND: requirement
BASE_UID: ARCH-AUTH-LOCAL
VERSION_N: 1
rbac_op: auth:local:signin, identity:account:manage
priority: 10
iteration: iter-r1
security.catalog_ref: AC-2
security.verification_note: AC-2 account management; CM-7 local accounts off by default; ASD V-222407 / V-222412 / V-222661.
edge: ← refines from ARCH-CRED-LOCKOUT
edge: ← uses from ARCH-DEVENV-IDENTITY.1
edge: ← refines from ARCH-AUTH-LOCAL-BREAKGLASS
edge: ← uses from FIX-DENY-LOCAL-LOGIN-PROFILE-OFF
edge: ← satisfies from CAP-CRED-STORE
in_scope_of_contract: ReqALM product (build)
delivered_by_release: R1 — foundation shell + internal auth
edge: → conforms_to to AC-2 (pin imprint=nist-800-53@rev5-dogfood-20261006)
edge: → conforms_to to IA-2 (pin imprint=nist-800-53@rev5-dogfood-20261006)
edge: → conforms_to to CM-7 (pin imprint=nist-800-53@rev5-dogfood-20261006)
edge: → conforms_to to V-222407 (pin imprint=asd-stig@v6r4)
edge: → conforms_to to V-222412 (pin imprint=asd-stig@v6r4)
edge: → conforms_to to V-222661 (pin imprint=asd-stig@v6r4)
<<<
RELATIONS:
- TYPE: Parent
  VALUE: ARCH-AUTH-AS
- TYPE: Parent
  VALUE: ARCH-AUTH-AS
  ROLE: Refines
- TYPE: Parent
  VALUE: ARCH-CRED
  ROLE: Uses
- TYPE: Parent
  VALUE: ARCH-AUTH-PROFILE
  ROLE: Uses
- TYPE: Parent
  VALUE: A01
  ROLE: Refines
- TYPE: Parent
  VALUE: ARCH-AUTH-LOCAL
  ROLE: Refines
- TYPE: Parent
  VALUE: AC-2
  ROLE: ConformsTo
- TYPE: Parent
  VALUE: IA-2
  ROLE: ConformsTo
- TYPE: Parent
  VALUE: CM-7
  ROLE: ConformsTo
- TYPE: Parent
  VALUE: V-222407
  ROLE: ConformsTo
- TYPE: Parent
  VALUE: V-222412
  ROLE: ConformsTo
- TYPE: Parent
  VALUE: V-222661
  ROLE: ConformsTo
- TYPE: Child
  VALUE: CONTRACT-ctr-reqalm-product
  ROLE: InScopeOf
- TYPE: Child
  VALUE: RELEASE-rel-r1-foundation-shell-auth
  ROLE: Delivers

[[SECTION]]
UID: ARCH-AUTH-LOCAL-CHILDREN
TITLE: Children of ARCH-AUTH-LOCAL

[REQUIREMENT]
UID: ARCH-AUTH-LOCAL-BREAKGLASS
STATUS: Active
TITLE: Break-glass local recovery admin (profile-enabled, MFA, dual control)
STATEMENT: >>>
When the auth profile sets local_accounts=breakglass_only or enabled, a deployment may configure break-glass local recovery admin accounts for when the upstream IdP or its connector is unavailable or misconfigured. These accounts are created only from deployment configuration, never through self-service or the dev seed. Their credentials are long random secrets held under split knowledge and dual control, the same custody model as ARCH-KEY-BREAKGLASS. MFA is always required (ARCH-CRED-MFA), and sessions use the admin idle and absolute timeouts (ARCH-CRED-SESSION). Privileges are limited to recovery operations (restore an upstream connector or admin grants), with no requirement-content access. Every use raises an alert, is audited (ARCH-CRED-AUDIT), and is reviewed, and the credential is rotated after use. Break-glass accounts are protected from removal or disabling except by the documented process, and are exercised on a schedule.
<<<
COMMENT: >>>
KIND: requirement
BASE_UID: ARCH-AUTH-LOCAL-BREAKGLASS
VERSION_N: 0
rbac_op: auth:breakglass:signin, auth:connector:configure
priority: 15
iteration: iter-r1
security.catalog_ref: AC-2.2
security.verification_note: AC-2(2) emergency accounts; IA-2(1) MFA; AU-2; ASD V-222410 / V-222523.
edge: ← uses from FIX-ALLOW-BREAKGLASS-LOCAL-ADMIN
in_scope_of_contract: ReqALM product (build)
delivered_by_release: R1 platform follow-ups (deferred from foundation PR)
edge: → conforms_to to AC-2.2 (pin imprint=nist-800-53@rev5-dogfood-20261006)
edge: → conforms_to to IA-2.1 (pin imprint=nist-800-53@rev5-dogfood-20261006)
edge: → conforms_to to AU-2 (pin imprint=nist-800-53@rev5-dogfood-20261006)
edge: → conforms_to to AC-5 (pin imprint=nist-800-53@rev5-dogfood-20261006)
edge: → conforms_to to V-222410 (pin imprint=asd-stig@v6r4)
edge: → conforms_to to V-222523 (pin imprint=asd-stig@v6r4)
edge: → conforms_to to V-222390 (pin imprint=asd-stig@v6r4)
<<<
RELATIONS:
- TYPE: Parent
  VALUE: ARCH-AUTH-LOCAL.1
- TYPE: Parent
  VALUE: ARCH-AUTH-LOCAL.1
  ROLE: Refines
- TYPE: Parent
  VALUE: ARCH-KEY-BREAKGLASS
  ROLE: Uses
- TYPE: Parent
  VALUE: ARCH-CRED-MFA
  ROLE: Uses
- TYPE: Parent
  VALUE: ARCH-CRED-SESSION
  ROLE: Uses
- TYPE: Parent
  VALUE: ARCH-CRED-AUDIT
  ROLE: Uses
- TYPE: Parent
  VALUE: AC-2.2
  ROLE: ConformsTo
- TYPE: Parent
  VALUE: IA-2.1
  ROLE: ConformsTo
- TYPE: Parent
  VALUE: AU-2
  ROLE: ConformsTo
- TYPE: Parent
  VALUE: AC-5
  ROLE: ConformsTo
- TYPE: Parent
  VALUE: V-222410
  ROLE: ConformsTo
- TYPE: Parent
  VALUE: V-222523
  ROLE: ConformsTo
- TYPE: Parent
  VALUE: V-222390
  ROLE: ConformsTo
- TYPE: Child
  VALUE: CONTRACT-ctr-reqalm-product
  ROLE: InScopeOf
- TYPE: Child
  VALUE: RELEASE-rel-r1-platform-followups
  ROLE: Delivers

[[/SECTION]]

[REQUIREMENT]
UID: ARCH-AUTH-PROFILE
STATUS: Active
TITLE: Auth profile: identity mode and local-account setting per deployment
STATEMENT: >>>
Each deployment has an auth profile that sets identity_mode (federated, local, or hybrid), local_accounts (disabled, breakglass_only, or enabled; see ARCH-AUTH-LOCAL.1), and the security presets (ARCH-CRED-POLICY / ARCH-CRED-MFA / ARCH-CRED-SESSION / ARCH-KEY-FIPS). Production defaults: identity_mode=federated, local_accounts=disabled. The profile is deployment configuration validated at startup, not a runtime toggle. A production profile that enables local accounts must name the reason and is logged at startup and in the audit trail. A dev profile (dev seed, dev KeyProvider) is refused in production. Whether a client tenant may override the deployment profile is an open question.
<<<
COMMENT: >>>
KIND: requirement
BASE_UID: ARCH-AUTH-PROFILE
VERSION_N: 0
rbac_op: auth:policy:configure
priority: 10
iteration: iter-r1
security.catalog_ref: CM-6
security.verification_note: CM-6 configuration settings; CM-7 least functionality (local accounts off by default).
edge: ← uses from ARCH-AUTH-LOCAL.1
edge: ← uses from ARCH-AUTH-MCP-REQUIRED
edge: ← uses from FIX-DENY-LOCAL-LOGIN-PROFILE-OFF
edge: ← uses from ARCH-BUILD-FOUNDATION
edge: ← satisfies from CAP-OAUTH-AS
in_scope_of_contract: ReqALM product (build)
delivered_by_release: R1 — foundation shell + internal auth
edge: → conforms_to to CM-6 (pin imprint=nist-800-53@rev5-dogfood-20261006)
edge: → conforms_to to CM-7 (pin imprint=nist-800-53@rev5-dogfood-20261006)
edge: → conforms_to to IA-2 (pin imprint=nist-800-53@rev5-dogfood-20261006)
<<<
RELATIONS:
- TYPE: Parent
  VALUE: ARCH-AUTH-AS
- TYPE: Parent
  VALUE: ARCH-AUTH-AS
  ROLE: Refines
- TYPE: Parent
  VALUE: A01
  ROLE: Refines
- TYPE: Parent
  VALUE: ARCH-CRED-POLICY
  ROLE: Uses
- TYPE: Parent
  VALUE: ARCH-KEY-FIPS
  ROLE: Uses
- TYPE: Parent
  VALUE: ARCH-DEVENV-IDENTITY.1
  ROLE: Uses
- TYPE: Parent
  VALUE: CM-6
  ROLE: ConformsTo
- TYPE: Parent
  VALUE: CM-7
  ROLE: ConformsTo
- TYPE: Parent
  VALUE: IA-2
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-AUTH-MCP-REQUIRED
STATUS: Active
TITLE: Internal AS is mandatory for MCP in every identity mode
STATEMENT: >>>
OAuth 2.1 through the internal AS (ARCH-AUTH-AS) is mandatory for MCP in every identity mode: federated, local, or hybrid. MCP hosts always authorize at the internal AS (ARCH-AUTH-PKCE / ARCH-AUTH-METADATA), and the MCP server accepts only internal-AS tokens whose audience is the MCP resource (ARCH-AUTH-AUDIENCE). How the user authenticates behind the AS (upstream IdP, or a local account where the profile allows it) never changes the MCP credential. Upstream provider tokens are never accepted by the MCP server and never forwarded by it. If an MCP tool must call an upstream provider's own APIs, the mechanism (token exchange vs stored upstream grants) is an open design choice (docs/design/auth/mcp-upstream-identity.md), but the AS token remains the MCP credential.
<<<
COMMENT: >>>
KIND: requirement
BASE_UID: ARCH-AUTH-MCP-REQUIRED
VERSION_N: 0
rbac_op: auth:oauth:authorize, mcp:session:create
priority: 5
iteration: iter-r1
security.catalog_ref: IA-2
security.verification_note: IA-2 / IA-8; SC-23 audience-bound session authenticity; MCP authorization spec (no token passthrough).
edge: ← uses from ARCH-AUTH-AGENT-ATTRIBUTION
edge: ← uses from FIX-ALLOW-MCP-OAUTH-FEDERATED-ONLY
edge: ← uses from ARCH-BUILD-FOUNDATION
edge: ← satisfies from CAP-OAUTH-AS
in_scope_of_contract: ReqALM product (build)
delivered_by_release: R1 — foundation shell + internal auth
edge: → conforms_to to IA-2 (pin imprint=nist-800-53@rev5-dogfood-20261006)
edge: → conforms_to to IA-8 (pin imprint=nist-800-53@rev5-dogfood-20261006)
edge: → conforms_to to SC-23 (pin imprint=nist-800-53@rev5-dogfood-20261006)
edge: → conforms_to to AC-3 (pin imprint=nist-800-53@rev5-dogfood-20261006)
edge: → conforms_to to V-222522 (pin imprint=asd-stig@v6r4)
<<<
RELATIONS:
- TYPE: Parent
  VALUE: ARCH-AUTH-AS
- TYPE: Parent
  VALUE: ARCH-AUTH-AS
  ROLE: Refines
- TYPE: Parent
  VALUE: MC01.1
  ROLE: Refines
- TYPE: Parent
  VALUE: CAP-MCP-DESK
  ROLE: Refines
- TYPE: Parent
  VALUE: ARCH-AUTH-AUDIENCE
  ROLE: Uses
- TYPE: Parent
  VALUE: ARCH-AUTH-PROFILE
  ROLE: Uses
- TYPE: Parent
  VALUE: IA-2
  ROLE: ConformsTo
- TYPE: Parent
  VALUE: IA-8
  ROLE: ConformsTo
- TYPE: Parent
  VALUE: SC-23
  ROLE: ConformsTo
- TYPE: Parent
  VALUE: AC-3
  ROLE: ConformsTo
- TYPE: Parent
  VALUE: V-222522
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-AUTH-AGENT-ATTRIBUTION
STATUS: Active
TITLE: Agent (MCP) actions attributed to the human subject and OAuth client
STATEMENT: >>>
Every action taken through MCP is attributed in audit to the human subject who authorized the MCP host (token sub), together with the OAuth client_id of the MCP host, the token id (jti), and source=mcp. There is no shared or elevated agent principal: an agent acts with the delegating user's grants under RBAC (MC01.1 / MC03). Attribution for headless or agent-only clients that act without a delegating human (client credentials, device flow) is an open question. Until it is decided, such clients are not supported.
<<<
COMMENT: >>>
KIND: requirement
BASE_UID: ARCH-AUTH-AGENT-ATTRIBUTION
VERSION_N: 0
rbac_op: audit:write
priority: 10
iteration: iter-r1
security.catalog_ref: AU-3
security.verification_note: AU-3 content of audit records; AU-10 non-repudiation; ASD V-222438.
edge: ← uses from FIX-ALLOW-AGENT-ATTRIBUTION
edge: ← satisfies from CAP-AGENT-ACCESS
edge: ← satisfies from CAP-TEST-AUTH-ROUTES
edge: ← satisfies from CAP-TEST-AUTH-HYGIENE
in_scope_of_contract: ReqALM product (build)
delivered_by_release: R1 — foundation shell + internal auth
edge: → conforms_to to AU-3 (pin imprint=nist-800-53@rev5-dogfood-20261006)
edge: → conforms_to to AU-10 (pin imprint=nist-800-53@rev5-dogfood-20261006)
edge: → conforms_to to IA-2 (pin imprint=nist-800-53@rev5-dogfood-20261006)
edge: → conforms_to to V-222438 (pin imprint=asd-stig@v6r4)
edge: → conforms_to to V-222441 (pin imprint=asd-stig@v6r4)
<<<
RELATIONS:
- TYPE: Parent
  VALUE: ARCH-AUTH-AS
- TYPE: Parent
  VALUE: ARCH-CRED-AUDIT
  ROLE: Refines
- TYPE: Parent
  VALUE: ARCH-AUTH-MCP-REQUIRED
  ROLE: Uses
- TYPE: Parent
  VALUE: MC02
  ROLE: Uses
- TYPE: Parent
  VALUE: ARCH-OTEL
  ROLE: Uses
- TYPE: Parent
  VALUE: AU-3
  ROLE: ConformsTo
- TYPE: Parent
  VALUE: AU-10
  ROLE: ConformsTo
- TYPE: Parent
  VALUE: IA-2
  ROLE: ConformsTo
- TYPE: Parent
  VALUE: V-222438
  ROLE: ConformsTo
- TYPE: Parent
  VALUE: V-222441
  ROLE: ConformsTo
- TYPE: Child
  VALUE: CONTRACT-ctr-reqalm-product
  ROLE: InScopeOf
- TYPE: Child
  VALUE: RELEASE-rel-r1-foundation-shell-auth
  ROLE: Delivers

[[/SECTION]]

[REQUIREMENT]
UID: CAP-OAUTH-AS
STATUS: Active
TITLE: Internal OAuth 2.1 authorization server
STATEMENT: >>>
ReqAML's internal OAuth 2.1 AS in the API role is the single token issuer for Web UI, API, and MCP: authorization code + PKCE S256 only, RFC 8414 AS metadata, RFC 9728 protected-resource metadata for API and MCP, RFC 8707 resource indicators with audience-bound access tokens, refresh-token rotation with reuse detection (family revocation), RFC 7009 revocation, pre-registered clients, dynamic client registration disabled by default. Acceptance: auth-flow-smoke covers AS01 beds (PKCE, refresh/reuse, revoke, wrong audience).
<<<
COMMENT: >>>
KIND: capability
BASE_UID: CAP-OAUTH-AS
VERSION_N: 0
priority: 10
iteration: iter-r1
security.catalog_ref: IA-2
security.verification_note: IA-2 / SC-23 OAuth beds. Verified: Local Docker 2026-10-07 on PR #13 follow-up (6a5f0db + verification fixes), fresh volumes: `pnpm devenv:init` idempotent (byte-identical rerun), `--rotate` issues new secrets (needs `down -v` for the Postgres volume), secrets files mode 600 and gitignored; `docker compose up --build -d --wait` with and without the hostports overlay (app 127.0.0.1:3000 only; peripherals unpublished without the overlay, loopback-only with it); /ready all green, restart count 0; `pnpm devenv:smoke` pass incl. auth-flow-smoke (server-side OAuth handoffs, PKCE S256, refresh rotation/reuse family revoke, RFC7009 refresh+access revoke, lockout + username normalize, Reader RBAC 403, wrong audience 401 at MCP, upstream connectors 401 unauthenticated, session cookie HttpOnly+SameSite=Lax, cookie mutation without CSRF 401, signout ends session, sam-security MFA login via `devenv:mfa`, TOTP replay rejected (and one wrong code does not lock the account), agent tokens default Reader / Author max / Developer+ refused, TTL <= 1h, agent token revoked 401), auth_audit_events incl. agent-attributed mutation, IP throttle 200 -> 401 after 20 failures, production refused dev accounts/keys, missing REQALM_ISSUER_URL and blanket trustProxy; headless Chrome first-login TOTP enrollment (jamie-ao) then MFA re-login; `@reqalm/app` test 30/30, typecheck pass; seed yaml_to_strictdoc --validate pass.
in_scope_of_contract: ReqALM product (build)
delivered_by_release: R1 — foundation shell + internal auth
edge: → conforms_to to IA-2 (pin imprint=nist-800-53@rev5-dogfood-20261006)
<<<
RELATIONS:
- TYPE: Parent
  VALUE: SEC-IA
- TYPE: Parent
  VALUE: ARCH-AUTH-AS
  ROLE: Satisfies
- TYPE: Parent
  VALUE: ARCH-AUTH-PKCE
  ROLE: Satisfies
- TYPE: Parent
  VALUE: ARCH-AUTH-METADATA
  ROLE: Satisfies
- TYPE: Parent
  VALUE: ARCH-AUTH-AUDIENCE
  ROLE: Satisfies
- TYPE: Parent
  VALUE: ARCH-AUTH-REFRESH
  ROLE: Satisfies
- TYPE: Parent
  VALUE: ARCH-AUTH-REVOKE
  ROLE: Satisfies
- TYPE: Parent
  VALUE: ARCH-AUTH-CLIENTREG
  ROLE: Satisfies
- TYPE: Parent
  VALUE: ARCH-AUTH-MCP-REQUIRED
  ROLE: Satisfies
- TYPE: Parent
  VALUE: ARCH-AUTH-PROFILE
  ROLE: Satisfies
- TYPE: Parent
  VALUE: IA-2
  ROLE: ConformsTo
- TYPE: Child
  VALUE: CONTRACT-ctr-reqalm-product
  ROLE: InScopeOf
- TYPE: Child
  VALUE: RELEASE-rel-r1-foundation-shell-auth
  ROLE: Delivers

[REQUIREMENT]
UID: CAP-AUTH-UPSTREAM-SEAM
STATUS: Active
TITLE: Pluggable upstream IdP connector seam (stub)
STATEMENT: >>>
Upstream federation is not fully implemented in R1; the `UpstreamConnector` interface and `upstream_connectors` table plus read-only listing API document the extension point without token passthrough. OIDC/SAML RP implementations and home-realm discovery are deferred.
<<<
COMMENT: >>>
KIND: capability
BASE_UID: CAP-AUTH-UPSTREAM-SEAM
VERSION_N: 0
priority: 10
iteration: iter-r1
security.catalog_ref: IA-8
security.verification_note: Seam only — no live federation in R1. Verified by code review + typecheck.
in_scope_of_contract: ReqALM product (build)
delivered_by_release: R1 — foundation shell + internal auth
edge: → conforms_to to IA-8 (pin imprint=nist-800-53@rev5-dogfood-20261006)
<<<
RELATIONS:
- TYPE: Parent
  VALUE: SEC-IA
- TYPE: Parent
  VALUE: ARCH-AUTH-UPSTREAM-CONNECTOR
  ROLE: Satisfies
- TYPE: Parent
  VALUE: IA-8
  ROLE: ConformsTo
- TYPE: Child
  VALUE: CONTRACT-ctr-reqalm-product
  ROLE: InScopeOf
- TYPE: Child
  VALUE: RELEASE-rel-r1-foundation-shell-auth
  ROLE: Delivers

[REQUIREMENT]
UID: CAP-MFA-ENROLL
STATUS: Active
TITLE: TOTP MFA enrollment (UI + devenv:mfa CLI)
STATEMENT: >>>
Privileged roles require MFA in all modes. First login can return `mfa_enrollment_required` with otpauth URI; the sign-in card shows a setup key and the otpauth URI (no QR code) and asks for the 6-digit code. `pnpm devenv:mfa <identity-id>` enrolls dev users inside the app container (or `--interactive` prints the URI + ticket, confirmed with `--ticket=… --confirm=<code>`). TOTP secrets are envelope-encrypted; a code is accepted once (replay of the matched time step is rejected).
<<<
COMMENT: >>>
KIND: capability
BASE_UID: CAP-MFA-ENROLL
VERSION_N: 0
priority: 10
iteration: iter-r1
security.catalog_ref: IA-2
security.verification_note: IA-2 MFA enrollment. Verified: Local Docker 2026-10-07 on PR #13 follow-up (6a5f0db + verification fixes), fresh volumes: `pnpm devenv:init` idempotent (byte-identical rerun), `--rotate` issues new secrets (needs `down -v` for the Postgres volume), secrets files mode 600 and gitignored; `docker compose up --build -d --wait` with and without the hostports overlay (app 127.0.0.1:3000 only; peripherals unpublished without the overlay, loopback-only with it); /ready all green, restart count 0; `pnpm devenv:smoke` pass incl. auth-flow-smoke (server-side OAuth handoffs, PKCE S256, refresh rotation/reuse family revoke, RFC7009 refresh+access revoke, lockout + username normalize, Reader RBAC 403, wrong audience 401 at MCP, upstream connectors 401 unauthenticated, session cookie HttpOnly+SameSite=Lax, cookie mutation without CSRF 401, signout ends session, sam-security MFA login via `devenv:mfa`, TOTP replay rejected (and one wrong code does not lock the account), agent tokens default Reader / Author max / Developer+ refused, TTL <= 1h, agent token revoked 401), auth_audit_events incl. agent-attributed mutation, IP throttle 200 -> 401 after 20 failures, production refused dev accounts/keys, missing REQALM_ISSUER_URL and blanket trustProxy; headless Chrome first-login TOTP enrollment (jamie-ao) then MFA re-login; `@reqalm/app` test 30/30, typecheck pass; seed yaml_to_strictdoc --validate pass.
edge: ← satisfies from CAP-MFA-QR
in_scope_of_contract: ReqALM product (build)
delivered_by_release: R1 — foundation shell + internal auth
edge: → conforms_to to IA-2 (pin imprint=nist-800-53@rev5-dogfood-20261006)
<<<
RELATIONS:
- TYPE: Parent
  VALUE: SEC-IA
- TYPE: Parent
  VALUE: ARCH-CRED-MFA
  ROLE: Satisfies
- TYPE: Parent
  VALUE: IA-2
  ROLE: ConformsTo
- TYPE: Child
  VALUE: CONTRACT-ctr-reqalm-product
  ROLE: InScopeOf
- TYPE: Child
  VALUE: RELEASE-rel-r1-foundation-shell-auth
  ROLE: Delivers

[REQUIREMENT]
UID: CAP-AGENT-ACCESS
STATUS: Active
TITLE: Dev agent OAuth client_credentials tokens
STATEMENT: >>>
`pnpm devenv:agent-token --agent <name> [--role Reader|Author]` mints short-lived (<= 1 h) audience-bound tokens via registered `reqaml-agent-dev` client_credentials (not a backdoor password). The agent is its own principal (`agent-<name>`) with explicit project grants; each token carries one role (default Reader), roles above Author or not granted are refused, and authorization uses only the token's role. Agent name, token role and optional acting-for are recorded on token issue and mutation audit.
<<<
COMMENT: >>>
KIND: capability
BASE_UID: CAP-AGENT-ACCESS
VERSION_N: 0
priority: 10
iteration: iter-r1
security.catalog_ref: IA-2
security.verification_note: IA-2 agent attribution. Verified: Local Docker 2026-10-07 on PR #13 follow-up (6a5f0db + verification fixes), fresh volumes: `pnpm devenv:init` idempotent (byte-identical rerun), `--rotate` issues new secrets (needs `down -v` for the Postgres volume), secrets files mode 600 and gitignored; `docker compose up --build -d --wait` with and without the hostports overlay (app 127.0.0.1:3000 only; peripherals unpublished without the overlay, loopback-only with it); /ready all green, restart count 0; `pnpm devenv:smoke` pass incl. auth-flow-smoke (server-side OAuth handoffs, PKCE S256, refresh rotation/reuse family revoke, RFC7009 refresh+access revoke, lockout + username normalize, Reader RBAC 403, wrong audience 401 at MCP, upstream connectors 401 unauthenticated, session cookie HttpOnly+SameSite=Lax, cookie mutation without CSRF 401, signout ends session, sam-security MFA login via `devenv:mfa`, TOTP replay rejected (and one wrong code does not lock the account), agent tokens default Reader / Author max / Developer+ refused, TTL <= 1h, agent token revoked 401), auth_audit_events incl. agent-attributed mutation, IP throttle 200 -> 401 after 20 failures, production refused dev accounts/keys, missing REQALM_ISSUER_URL and blanket trustProxy; headless Chrome first-login TOTP enrollment (jamie-ao) then MFA re-login; `@reqalm/app` test 30/30, typecheck pass; seed yaml_to_strictdoc --validate pass.
in_scope_of_contract: ReqALM product (build)
delivered_by_release: R1 — foundation shell + internal auth
edge: → conforms_to to IA-2 (pin imprint=nist-800-53@rev5-dogfood-20261006)
<<<
RELATIONS:
- TYPE: Parent
  VALUE: SEC-IA
- TYPE: Parent
  VALUE: ARCH-AUTH-AGENT-ATTRIBUTION
  ROLE: Satisfies
- TYPE: Parent
  VALUE: IA-2
  ROLE: ConformsTo
- TYPE: Child
  VALUE: CONTRACT-ctr-reqalm-product
  ROLE: InScopeOf
- TYPE: Child
  VALUE: RELEASE-rel-r1-foundation-shell-auth
  ROLE: Delivers

[REQUIREMENT]
UID: CAP-AUTH-HARDEN
STATUS: Draft
TITLE: Auth hardening: handoffs, BFF session, throttle, prod issuer
STATEMENT: >>>
Server-side OAuth login handoffs (no browser-trusted redirect_uri), HttpOnly web session cookies with CSRF required on every cookie-authenticated mutation, per-IP failed-login throttle alongside account lockout, prod REQAML_ISSUER_URL self-check, trustProxy off by default (production requires an explicit REQAML_TRUSTED_PROXIES list), auth on upstream connector listing, auth code redaction in logs, hashed unknown-usernames on failure audit, JWT signature verify before access-token revocation, normalized usernames.
<<<
COMMENT: >>>
KIND: capability
BASE_UID: CAP-AUTH-HARDEN
VERSION_N: 0
priority: 10
iteration: iter-r1
security.catalog_ref: SC-23
security.verification_note: SC-23 session/OAuth hardening. Verified: Local Docker 2026-10-07 on PR #13 follow-up (6a5f0db + verification fixes), fresh volumes: `pnpm devenv:init` idempotent (byte-identical rerun), `--rotate` issues new secrets (needs `down -v` for the Postgres volume), secrets files mode 600 and gitignored; `docker compose up --build -d --wait` with and without the hostports overlay (app 127.0.0.1:3000 only; peripherals unpublished without the overlay, loopback-only with it); /ready all green, restart count 0; `pnpm devenv:smoke` pass incl. auth-flow-smoke (server-side OAuth handoffs, PKCE S256, refresh rotation/reuse family revoke, RFC7009 refresh+access revoke, lockout + username normalize, Reader RBAC 403, wrong audience 401 at MCP, upstream connectors 401 unauthenticated, session cookie HttpOnly+SameSite=Lax, cookie mutation without CSRF 401, signout ends session, sam-security MFA login via `devenv:mfa`, TOTP replay rejected (and one wrong code does not lock the account), agent tokens default Reader / Author max / Developer+ refused, TTL <= 1h, agent token revoked 401), auth_audit_events incl. agent-attributed mutation, IP throttle 200 -> 401 after 20 failures, production refused dev accounts/keys, missing REQALM_ISSUER_URL and blanket trustProxy; headless Chrome first-login TOTP enrollment (jamie-ao) then MFA re-login; `@reqalm/app` test 30/30, typecheck pass; seed yaml_to_strictdoc --validate pass.
edge: ← refines from CAP-AUTH-HARDEN.1
delivered_by_release: R1 — foundation shell + internal auth
edge: → conforms_to to SC-23 (pin imprint=nist-800-53@rev5-dogfood-20261006)
<<<
RELATIONS:
- TYPE: Parent
  VALUE: SEC-IA
- TYPE: Parent
  VALUE: ARCH-AUTH-AS
  ROLE: Satisfies
- TYPE: Parent
  VALUE: ARCH-CRED-LOCKOUT
  ROLE: Satisfies
- TYPE: Parent
  VALUE: SC-23
  ROLE: ConformsTo
- TYPE: Child
  VALUE: RELEASE-rel-r1-foundation-shell-auth
  ROLE: Delivers

[REQUIREMENT]
UID: CAP-AUTH-HARDEN.1
STATUS: Active
TITLE: Auth hardening: handoffs, BFF session, throttle, prod issuer
STATEMENT: >>>
Server-side OAuth login handoffs (no browser-trusted redirect_uri), HttpOnly web session cookies with CSRF required on every cookie-authenticated mutation, per-IP failed-login throttle alongside account lockout, prod REQAML_ISSUER_URL self-check, trustProxy off by default (production requires an explicit REQAML_TRUSTED_PROXIES list), auth on upstream connector listing, auth code redaction in logs, hashed unknown-usernames on failure audit, JWT signature verify before access-token revocation, normalized usernames.
<<<
COMMENT: >>>
KIND: capability
BASE_UID: CAP-AUTH-HARDEN
VERSION_N: 1
priority: 10
iteration: iter-r1
security.catalog_ref: SC-23
security.verification_note: security_meta mint: inheritable SC-23 for uses inheritance seed bed.
edge: ← uses from CAP-UI-FRAME.1
edge: ← uses from CAP-UI-FRAME.2
in_scope_of_contract: ReqALM product (build)
edge: → conforms_to to SC-23 (pin imprint=nist-800-53@rev5-dogfood-20261006 inheritable)
<<<
RELATIONS:
- TYPE: Parent
  VALUE: SEC-IA
- TYPE: Parent
  VALUE: CAP-AUTH-HARDEN
  ROLE: Refines
- TYPE: Parent
  VALUE: ARCH-AUTH-AS
  ROLE: Satisfies
- TYPE: Parent
  VALUE: ARCH-CRED-LOCKOUT
  ROLE: Satisfies
- TYPE: Parent
  VALUE: SC-23
  ROLE: ConformsTo
- TYPE: Child
  VALUE: CONTRACT-ctr-reqalm-product
  ROLE: InScopeOf

[REQUIREMENT]
UID: CAP-TEST-AUTH-ROUTES
STATUS: Active
TITLE: In-process auth route integration tests
STATEMENT: >>>
Fastify `inject` exercises OAuth authorize/token, local login, web session CSRF, and agent client_credentials without network or Docker.
<<<
COMMENT: >>>
KIND: capability
BASE_UID: CAP-TEST-AUTH-ROUTES
VERSION_N: 0
priority: 10
iteration: iter-r1
security.catalog_ref: IA-2
security.verification_note: Regression beds for R1 auth. Verified: 2026-10-07 cloud agent VM (no Docker): `pnpm test` pass — @reqalm/app 38/38 incl. auth.integration.test.ts (8 in-process Fastify inject cases: PKCE/redirect_uri, refresh reuse, lockout, IP throttle failures-only, TOTP replay, CSRF cookie mutations, agent token roles/TTL/audience); PGlite runs real SQL migrations; createMemoryKeyProvider wrap/unwrap; typecheck pass.
in_scope_of_contract: ReqALM product (build)
delivered_by_release: R1 — in-process test harness (no Docker)
<<<
RELATIONS:
- TYPE: Parent
  VALUE: SEC-IA
- TYPE: Parent
  VALUE: ARCH-AUTH-PKCE
  ROLE: Satisfies
- TYPE: Parent
  VALUE: ARCH-AUTH-REFRESH
  ROLE: Satisfies
- TYPE: Parent
  VALUE: ARCH-CRED-LOCKOUT
  ROLE: Satisfies
- TYPE: Parent
  VALUE: ARCH-CRED-MFA
  ROLE: Satisfies
- TYPE: Parent
  VALUE: ARCH-AUTH-AGENT-ATTRIBUTION
  ROLE: Satisfies
- TYPE: Child
  VALUE: CONTRACT-ctr-reqalm-product
  ROLE: InScopeOf
- TYPE: Child
  VALUE: RELEASE-rel-r1-test-harness
  ROLE: Delivers

[REQUIREMENT]
UID: CAP-TEST-AUTH-HYGIENE
STATUS: Active
TITLE: Stronger in-process auth regression beds
STATEMENT: >>>
In-process auth.integration tests cover lockout window boundaries (SQL clock, no real sleep), username-normalization lockout HTTP 423, MCP audience accept/reject pairs, and agent access-token revocation returning 401 on `/api/v1/me`.
<<<
COMMENT: >>>
KIND: capability
BASE_UID: CAP-TEST-AUTH-HYGIENE
VERSION_N: 0
priority: 10
iteration: iter-r1
security.catalog_ref: IA-2
security.verification_note: Verified: 2026-10-07 cloud agent VM (no Docker): `pnpm test` pass (@reqalm/app 39/39 incl. expanded auth.integration.test.ts); `pnpm typecheck` pass.
in_scope_of_contract: ReqALM product (build)
delivered_by_release: R1 — test/build hygiene (Docker-free test follow-ups)
<<<
RELATIONS:
- TYPE: Parent
  VALUE: SEC-IA
- TYPE: Parent
  VALUE: ARCH-CRED-LOCKOUT
  ROLE: Satisfies
- TYPE: Parent
  VALUE: ARCH-AUTH-AUDIENCE
  ROLE: Satisfies
- TYPE: Parent
  VALUE: ARCH-AUTH-REVOKE
  ROLE: Satisfies
- TYPE: Parent
  VALUE: ARCH-AUTH-AGENT-ATTRIBUTION
  ROLE: Satisfies
- TYPE: Child
  VALUE: CONTRACT-ctr-reqalm-product
  ROLE: InScopeOf
- TYPE: Child
  VALUE: RELEASE-rel-r1-test-hygiene
  ROLE: Delivers

[REQUIREMENT]
UID: CAP-MFA-QR
STATUS: Active
TITLE: MFA enrollment QR code (sign-in UI)
STATEMENT: >>>
MFA enrollment on the sign-in card renders a scannable QR code for the otpauth URI locally in the browser (vendored MIT qr-min matrix encoder to SVG; no external QR service or network fetch). Setup key and manual otpauth URI remain visible for copy/paste. Enrollment JSON responses use Cache-Control: no-store; QR markup is removed from the DOM after successful enrollment. Accessible name on the QR image; CSP-safe (same-origin module, DOM-built SVG, no inline handlers).
<<<
COMMENT: >>>
KIND: capability
BASE_UID: CAP-MFA-QR
VERSION_N: 0
priority: 10
iteration: iter-r1
security.catalog_ref: IA-2
security.verification_note: Shipped with MFA enrollment QR PR #30 (merge c8668b924ba4804e32f4d364aa0d343af60e9f83).
in_scope_of_contract: ReqALM product (build)
delivered_by_release: R1 — MFA enrollment QR (sign-in UI)
<<<
RELATIONS:
- TYPE: Parent
  VALUE: SEC-IA
- TYPE: Parent
  VALUE: CAP-MFA-ENROLL
  ROLE: Satisfies
- TYPE: Parent
  VALUE: ARCH-CRED-MFA
  ROLE: Satisfies
- TYPE: Parent
  VALUE: ARCH-UI-GUARD
  ROLE: Satisfies
- TYPE: Child
  VALUE: CONTRACT-ctr-reqalm-product
  ROLE: InScopeOf
- TYPE: Child
  VALUE: RELEASE-rel-r1-mfa-qr
  ROLE: Delivers

[REQUIREMENT]
UID: CAP-READ-ACCESS
STATUS: Draft
TITLE: Read people and access (grants, roles, platform)
STATEMENT: >>>
Grant-scoped read-only people/access API: project people and grants, client grants, role catalog with permissions, and platform grants visible only to platform roles. RBAC grant:read; missing/forbidden project access returns 404; responses omit credential, session, and signing material.
<<<
COMMENT: >>>
KIND: capability
BASE_UID: CAP-READ-ACCESS
VERSION_N: 0
priority: 10
iteration: iter-r1
security.catalog_ref: AC-3
security.verification_note: Planned until people/access read API PR merges.
<<<
RELATIONS:
- TYPE: Parent
  VALUE: SEC-IA
- TYPE: Parent
  VALUE: A11
  ROLE: Satisfies
- TYPE: Parent
  VALUE: CAP-RBAC
  ROLE: Satisfies
- TYPE: Parent
  VALUE: CAP-SVC-OPERATION-ROUTE
  ROLE: Satisfies

[[/SECTION]]

[[SECTION]]
UID: SEC-CP
TITLE: Client & Project

[TEXT]
UID: SEC-CP-INTRO
STATEMENT: >>>
Client owns projects; all project work assumes a Client Scoped View. Client and project CRUD, archive, and permission-filtered listing live here.
<<<

[REQUIREMENT]
UID: B01
STATUS: Active
TITLE: Create client
STATEMENT: >>>
A client admin creates a new client. ReqAML inserts a client row with stable id and display name,
audits the create, and does not auto-create projects. Project grants remain explicit after create.
<<<
COMMENT: >>>
KIND: requirement
BASE_UID: B01
VERSION_N: 0
rbac_op: client:create
priority: 20
iteration: iter-r1
security.catalog_ref: AC-3
security.verification_note: AC-3 client create gated to client admins. AU-2/3/12.
edge: ← uses from FIX-ALLOW-CLIENT-CREATE
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CP
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: B02
STATUS: Active
TITLE: Update client metadata
STATEMENT: >>>
A client admin updates client display name or metadata. ReqAML persists the change without altering
project membership or grants. The update is audited (actor, client_id, fields). Pat Client-Admin on
raby-family is the dogfood actor for client-level mutations.
<<<
COMMENT: >>>
KIND: requirement
BASE_UID: B02
VERSION_N: 0
rbac_op: client:update
priority: 40
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CP
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: B03
STATUS: Active
TITLE: Archive / deactivate client
STATEMENT: >>>
A client admin archives or deactivates a client. ReqAML marks the client inactive, blocks new project
creates under it, and refuses Scoped View selection for archived clients. Existing project data is retained.
<<<
COMMENT: >>>
KIND: requirement
BASE_UID: B03
VERSION_N: 0
rbac_op: client:archive
priority: 60
iteration: iter-r2
security.catalog_ref: AC-3
security.verification_note: Archive blocks new scope binds; AU on archive action.
in_scope_of_contract: ReqALM product (build)
edge: → conforms_to to AC-3 (pin imprint=nist-800-53@rev5-dogfood-20261006)
<<<
RELATIONS:
- TYPE: Parent
  VALUE: SEC-CP
- TYPE: Parent
  VALUE: AC-3
  ROLE: ConformsTo
- TYPE: Child
  VALUE: CONTRACT-ctr-reqalm-product
  ROLE: InScopeOf

[REQUIREMENT]
UID: B04
STATUS: Active
TITLE: Create project under client
STATEMENT: >>>
A Project admin creates a project under the scoped client. ReqAML inserts a project row; grants are
not auto-created beyond the creating admin policy already decided. Create is audited and AC-3 gated.
<<<
COMMENT: >>>
KIND: requirement
BASE_UID: B04
VERSION_N: 0
rbac_op: project:create
priority: 15
iteration: iter-r0
security.catalog_ref: AC-3
security.verification_note: AC-3 access enforcement; AU-2/3/12 where mutating.
in_scope_of_contract: Design-2026-10
in_scope_of_contract: Platform baseline
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CP
- TYPE: Parent
  VALUE: ARCH-CP-HIER
  ROLE: Refines
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r1-core-alm
  ROLE: Delivers

[REQUIREMENT]
UID: B05
STATUS: Active
TITLE: Update project
STATEMENT: >>>
A Project admin updates project display name or notes. ReqAML persists metadata without moving the
project across clients. Updates are audited.
<<<
COMMENT: >>>
KIND: requirement
BASE_UID: B05
VERSION_N: 0
rbac_op: project:update
priority: 40
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CP
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: B06
STATUS: Active
TITLE: Archive project
STATEMENT: >>>
A Project admin archives a project. ReqAML marks the project inactive and blocks new mutating work
while preserving historical versions, contracts, and releases. Archive is audited.
<<<
COMMENT: >>>
KIND: requirement
BASE_UID: B06
VERSION_N: 0
rbac_op: project:archive
priority: 60
iteration: iter-r2
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CP
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: B07
STATUS: Active
TITLE: List clients (permission-filtered)
STATEMENT: >>>
An authenticated user lists clients they are allowed to see. ReqAML returns only clients where the
caller has a grant or client-admin binding — never a global client dump for ordinary users.
<<<
COMMENT: >>>
KIND: requirement
BASE_UID: B07
VERSION_N: 0
rbac_op: client:list
priority: 25
iteration: iter-r0
security.catalog_ref: AC-3
security.verification_note: Permission-filtered list; no cross-tenant leakage.
edge: ← satisfies from CAP-BROWSE-CP
edge: ← satisfies from CAP-BROWSE-UI-CP
edge: ← satisfies from CAP-BROWSE-UI-CP.1
in_scope_of_contract: Design-2026-10
in_scope_of_contract: Platform baseline
in_scope_of_contract: ReqALM product (build)
delivered_by_release: R1-core-ALM
edge: → conforms_to to AC-3 (pin imprint=nist-800-53@rev5-dogfood-20261006)
<<<
RELATIONS:
- TYPE: Parent
  VALUE: SEC-CP
- TYPE: Parent
  VALUE: AC-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r1-core-alm
  ROLE: Delivers

[REQUIREMENT]
UID: B08
STATUS: Active
TITLE: List projects in scoped client
STATEMENT: >>>
A Reader lists projects in the scoped client. ReqAML returns only projects the caller can access
under active grants within the bound client — never a cross-client dump.
<<<
COMMENT: >>>
KIND: requirement
BASE_UID: B08
VERSION_N: 0
rbac_op: project:list
priority: 25
iteration: iter-r0
security.catalog_ref: AC-3
security.verification_note: AC-3 access enforcement; AU-2/3/12 where mutating.
edge: ← satisfies from CAP-BROWSE-CP
edge: ← satisfies from CAP-BROWSE-UI-CP
edge: ← satisfies from CAP-BROWSE-UI-CP.1
in_scope_of_contract: Design-2026-10
in_scope_of_contract: Platform baseline
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CP
- TYPE: Parent
  VALUE: A03
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r1-core-alm
  ROLE: Delivers

[REQUIREMENT]
UID: ARCH-CP-HIER
STATUS: Active
TITLE: Client → Project hierarchy
STATEMENT: >>>
ReqAML organizes work as Client → Project. Projects belong to exactly one client; Client Scoped View
is assumed for most project operations. UI and API both refuse cross-client project joins.
<<<
COMMENT: >>>
KIND: requirement
BASE_UID: ARCH-CP-HIER
VERSION_N: 0
priority: 5
iteration: iter-r0
security.catalog_ref: AC-3
security.verification_note: AC-3 access enforcement; AU-2/3/12 where mutating.
edge: ← uses from ARCH-UI
edge: ← refines from A03
edge: ← refines from B04
edge: ← satisfies from CAP-BROWSE-CP
in_scope_of_contract: Design-2026-10
in_scope_of_contract: Platform baseline
in_scope_of_contract: ReqALM product (build)
delivered_by_release: R0-sequences
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CP
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r0-sequences
  ROLE: Delivers

[[SECTION]]
UID: ARCH-CP-HIER-CHILDREN
TITLE: Children of ARCH-CP-HIER

[REQUIREMENT]
UID: ARCH-CP-SCOPE
STATUS: Active
TITLE: Server-bound clientId + mandatory client_id / RLS
STATEMENT: >>>
Active clientId lives on the server session (not only in browser local storage). Business services and the data layer enforce client scope: every query carries a mandatory client_id predicate (repository filter and/or Postgres RLS). Search, audit, catalogs, grants, and imprint reads never cross clients. Least privilege cannot be bypassed by crafting URLs. Cross-client denial beds: FIX-DENY-CROSS-CLIENT / FIX-DENY-AUDIT-CROSS-CLIENT.
<<<
COMMENT: >>>
KIND: requirement
BASE_UID: ARCH-CP-SCOPE
VERSION_N: 0
rbac_op: client:scope:select
priority: 5
iteration: iter-r0
security.catalog_ref: REQALM-SEC-SCOPE
security.verification_note: Maps to ReqALM project catalog SCOPE item.
edge: ← refines from A03
edge: ← uses from ARCH-BUILD-FOUNDATION
edge: ← uses from ARCH-AUTH-UPSTREAM-CONNECTOR
edge: ← uses from FIX-DENY-CROSS-TENANT-CONNECTOR
edge: ← refines from ARCH-WRITE-TRUNCATE-GUARD
edge: ← refines from ARCH-ATTACH
in_scope_of_contract: Design-2026-10
in_scope_of_contract: Security package
in_scope_of_contract: ReqALM product (build)
delivered_by_release: R1-core-ALM
edge: → uses to CAP-SCOPED-VIEW (RELATIONS TYPE: Child; Parent would cycle)
edge: → conforms_to to AC-3 (pin imprint=nist-800-53@rev5-dogfood-20261006)
<<<
RELATIONS:
- TYPE: Parent
  VALUE: ARCH-CP-HIER
- TYPE: Parent
  VALUE: AC-3
  ROLE: ConformsTo
- TYPE: Child
  VALUE: CAP-SCOPED-VIEW
  ROLE: Uses
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r1-core-alm
  ROLE: Delivers

[REQUIREMENT]
UID: ARCH-HIER-REQ-DECOMP
STATUS: Active
TITLE: Requirement decomposition rollup
STATEMENT: >>>
Requirement lines may have child requirement lines (decomposition). Child requirements shall roll up completeness and status into the parent. Requirements shall nest only under requirements or sections, never under capability lines.
<<<
COMMENT: >>>
KIND: requirement
BASE_UID: ARCH-HIER-REQ-DECOMP
VERSION_N: 0
rbac_op: requirement:line:create
priority: 15
iteration: iter-r1
security.catalog_ref: CM-2
security.verification_note: Groomed 2026-10-09; pre-write or UI track.
in_scope_of_contract: ReqALM product (build)
<<<
RELATIONS:
- TYPE: Parent
  VALUE: ARCH-CP-HIER
- TYPE: Parent
  VALUE: C01
  ROLE: Refines
- TYPE: Child
  VALUE: CONTRACT-ctr-reqalm-product
  ROLE: InScopeOf

[REQUIREMENT]
UID: ARCH-HIER-CAP-PARTOF
STATUS: Active
TITLE: Capability part-of rollup
STATEMENT: >>>
Capability lines may have child capability lines (part-of composition). Child capabilities shall roll up operational/verification status into the parent. Child capabilities shall inherit the parent's conforms_to control pins unless a child override capability explicitly replaces them.
<<<
COMMENT: >>>
KIND: requirement
BASE_UID: ARCH-HIER-CAP-PARTOF
VERSION_N: 0
priority: 15
iteration: iter-r1
security.catalog_ref: CM-2
security.verification_note: Groomed 2026-10-09; pre-write or UI track. rbac_op capability:view proposed for future hierarchy browse.
edge: ← satisfies from CAP-UI-VIEW-CAP-DETAIL
edge: ← satisfies from CAP-UI-VIEW-CAP-FOCUS
in_scope_of_contract: ReqALM product (build)
<<<
RELATIONS:
- TYPE: Parent
  VALUE: ARCH-CP-HIER
- TYPE: Parent
  VALUE: ARCH-CAP-LINK
  ROLE: Refines
- TYPE: Child
  VALUE: CONTRACT-ctr-reqalm-product
  ROLE: InScopeOf

[REQUIREMENT]
UID: ARCH-HIER-SECTION-GROUP
STATUS: Active
TITLE: Sections group only (no rollup)
STATEMENT: >>>
Section lines shall group siblings only. Section placement shall not imply status rollup, control inheritance, or satisfies/conforms_to propagation.
<<<
COMMENT: >>>
KIND: requirement
BASE_UID: ARCH-HIER-SECTION-GROUP
VERSION_N: 0
rbac_op: requirement:tree:read
priority: 15
iteration: iter-r1
security.catalog_ref: CM-2
security.verification_note: Groomed 2026-10-09; pre-write or UI track.
in_scope_of_contract: ReqALM product (build)
<<<
RELATIONS:
- TYPE: Parent
  VALUE: ARCH-CP-HIER
- TYPE: Parent
  VALUE: ARCH-SUBJECT-KIND
  ROLE: Refines
- TYPE: Child
  VALUE: CONTRACT-ctr-reqalm-product
  ROLE: InScopeOf

[[/SECTION]]

[REQUIREMENT]
UID: CAP-BROWSE-CP
STATUS: Active
TITLE: Browse clients and projects (read-only)
STATEMENT: >>>
Grant-scoped read APIs: paged GET /api/v1/clients, /clients/:id, /projects, /clients/:id/projects; shared PageQuery (max 100); listScope routes filter by per-project permission (agent role narrowing); invalid slug redaction on /clients/ and /projects/ paths.
<<<
COMMENT: >>>
KIND: capability
BASE_UID: CAP-BROWSE-CP
VERSION_N: 0
priority: 10
iteration: iter-r1
security.catalog_ref: CM-2
security.verification_note: Shipped with browse-clients-projects PR #22.
edge: ← satisfies from CAP-BROWSE-UI-CP
edge: ← satisfies from CAP-BROWSE-UI-CP.1
in_scope_of_contract: ReqALM product (build)
delivered_by_release: R1 — browse clients and projects (read-only)
<<<
RELATIONS:
- TYPE: Parent
  VALUE: SEC-CP
- TYPE: Parent
  VALUE: B07
  ROLE: Satisfies
- TYPE: Parent
  VALUE: B08
  ROLE: Satisfies
- TYPE: Parent
  VALUE: ARCH-CP-HIER
  ROLE: Satisfies
- TYPE: Parent
  VALUE: CAP-SVC-PROJECT-READ
  ROLE: Satisfies
- TYPE: Child
  VALUE: CONTRACT-ctr-reqalm-product
  ROLE: InScopeOf
- TYPE: Child
  VALUE: RELEASE-rel-r1-browse-clients-projects
  ROLE: Delivers

[REQUIREMENT]
UID: CAP-BROWSE-UI-CP
STATUS: Draft
TITLE: Browse clients and projects UI (read-only)
STATEMENT: >>>
Read-only /app browse screens for grant-scoped clients and projects: paged clients list, client detail with projects, all-projects list with client name, and a project header stub (Requirements and Releases sections labelled coming next). Uses existing session/CSRF auth; API data rendered via safe DOM text only.
<<<
COMMENT: >>>
KIND: capability
BASE_UID: CAP-BROWSE-UI-CP
VERSION_N: 0
priority: 10
iteration: iter-r1
security.catalog_ref: CM-2
security.verification_note: Shipped with browse UI PR #23.
edge: ← refines from CAP-BROWSE-UI-CP.1
delivered_by_release: R1 — browse clients and projects UI (read-only)
<<<
RELATIONS:
- TYPE: Parent
  VALUE: SEC-CP
- TYPE: Parent
  VALUE: B07
  ROLE: Satisfies
- TYPE: Parent
  VALUE: B08
  ROLE: Satisfies
- TYPE: Parent
  VALUE: ARCH-UI
  ROLE: Satisfies
- TYPE: Parent
  VALUE: ARCH-UI-GUARD
  ROLE: Satisfies
- TYPE: Parent
  VALUE: CAP-BROWSE-CP
  ROLE: Satisfies
- TYPE: Child
  VALUE: RELEASE-rel-r1-browse-ui-cp
  ROLE: Delivers

[REQUIREMENT]
UID: CAP-BROWSE-UI-CP.1
STATUS: Active
TITLE: Browse clients and projects UI (read-only)
STATEMENT: >>>
Read-only /app browse screens for grant-scoped clients and projects: paged clients list, client detail with projects, all-projects list with client name, and a project header stub (Requirements and Releases sections labelled coming next). Uses existing session/CSRF auth; API data rendered via safe DOM text only. Layout: Clients entry lists grant-scoped clients; row opens client detail with projects table; All projects lists cross-client projects with client name; project stub shows Requirements/Releases placeholders linking into project routes. Header uses global Clients/Projects nav outside project tabs.
<<<
COMMENT: >>>
KIND: capability
BASE_UID: CAP-BROWSE-UI-CP
VERSION_N: 1
priority: 10
iteration: iter-r1
security.catalog_ref: CM-2
security.verification_note: Layout prose added 2026-10-10 seed (CAP-UI-LAYOUT); shipped browse UI PR #23.
in_scope_of_contract: ReqALM product (build)
<<<
RELATIONS:
- TYPE: Parent
  VALUE: SEC-CP
- TYPE: Parent
  VALUE: CAP-BROWSE-UI-CP
  ROLE: Refines
- TYPE: Parent
  VALUE: B07
  ROLE: Satisfies
- TYPE: Parent
  VALUE: B08
  ROLE: Satisfies
- TYPE: Parent
  VALUE: ARCH-UI
  ROLE: Satisfies
- TYPE: Parent
  VALUE: ARCH-UI-GUARD
  ROLE: Satisfies
- TYPE: Parent
  VALUE: CAP-BROWSE-CP
  ROLE: Satisfies
- TYPE: Child
  VALUE: CONTRACT-ctr-reqalm-product
  ROLE: InScopeOf

[REQUIREMENT]
UID: CAP-READ-REQS
STATUS: Active
TITLE: Read requirements (list, detail, versions)
STATEMENT: >>>
Grant-scoped requirements read APIs: paged GET /api/v1/projects/:projectId/requirements with filters (kind, type, status, q) and current-version summaries; GET detail (statement + version attributes); GET version history (newest first). listScope pipeline supplies allowedProjectIds for browse lists; trace edges are not persisted in the seed loader yet (deferred). Invalid requirement id segments redact in logs/spans like client/project slugs.
<<<
COMMENT: >>>
KIND: capability
BASE_UID: CAP-READ-REQS
VERSION_N: 0
priority: 10
iteration: iter-r1
security.catalog_ref: CM-2
security.verification_note: Shipped with requirements read API PR #24.
edge: ← satisfies from CAP-BROWSE-UI-REQS
edge: ← satisfies from CAP-READ-HIERARCHY
edge: ← satisfies from CAP-RELATIONS-API
edge: ← satisfies from CAP-CATALOGS-API
edge: ← satisfies from CAP-BROWSE-UI-REQS.1
edge: ← satisfies from CAP-READ-CONTRACTS
in_scope_of_contract: ReqALM product (build)
delivered_by_release: R1 — requirements read API
<<<
RELATIONS:
- TYPE: Parent
  VALUE: SEC-CP
- TYPE: Parent
  VALUE: C08
  ROLE: Satisfies
- TYPE: Parent
  VALUE: D06
  ROLE: Satisfies
- TYPE: Parent
  VALUE: ARCH-API-RBAC
  ROLE: Satisfies
- TYPE: Parent
  VALUE: CAP-SVC-OPERATION-ROUTE
  ROLE: Satisfies
- TYPE: Parent
  VALUE: CAP-RBAC
  ROLE: Satisfies
- TYPE: Child
  VALUE: CONTRACT-ctr-reqalm-product
  ROLE: InScopeOf
- TYPE: Child
  VALUE: RELEASE-rel-r1-read-requirements
  ROLE: Delivers

[REQUIREMENT]
UID: CAP-BROWSE-UI-REQS
STATUS: Draft
TITLE: Browse requirements UI (read-only)
STATEMENT: >>>
Read-only /app browse screens for grant-scoped requirements within a project: paged list with kind/type/status filters and q search (URL-driven), requirement detail (statement + attributes), and paged version history (newest first). Uses session/CSRF auth; safe DOM text only. Trace links deferred.
<<<
COMMENT: >>>
KIND: capability
BASE_UID: CAP-BROWSE-UI-REQS
VERSION_N: 0
priority: 10
iteration: iter-r1
security.catalog_ref: CM-2
security.verification_note: Shipped with requirements browse UI PR #26.
edge: ← satisfies from CAP-BROWSE-UI-RELATIONS
edge: ← satisfies from CAP-UI-HEADER-NAV
edge: ← refines from CAP-BROWSE-UI-REQS.1
edge: ← satisfies from CAP-BROWSE-UI-RELATIONS.1
edge: ← satisfies from CAP-UI-HEADER-NAV.1
edge: ← satisfies from CAP-BROWSE-UI-CATALOGS
edge: ← satisfies from CAP-BROWSE-UI-CONTRACTS
delivered_by_release: R1 — browse requirements UI (read-only)
<<<
RELATIONS:
- TYPE: Parent
  VALUE: SEC-CP
- TYPE: Parent
  VALUE: C08
  ROLE: Satisfies
- TYPE: Parent
  VALUE: D06
  ROLE: Satisfies
- TYPE: Parent
  VALUE: ARCH-UI
  ROLE: Satisfies
- TYPE: Parent
  VALUE: ARCH-UI-GUARD
  ROLE: Satisfies
- TYPE: Parent
  VALUE: CAP-READ-REQS
  ROLE: Satisfies
- TYPE: Child
  VALUE: RELEASE-rel-r1-browse-ui-reqs
  ROLE: Delivers

[REQUIREMENT]
UID: CAP-BROWSE-UI-REQS.1
STATUS: Active
TITLE: Browse requirements UI (read-only)
STATEMENT: >>>
Read-only /app browse screens for grant-scoped requirements within a project: paged list with kind/type/status filters and q search (URL-driven), requirement detail (statement + attributes), and paged version history (newest first). Uses session/CSRF auth; safe DOM text only. Trace links deferred. Layout: Project Requirements tab — filter strip (kind/type/status/q) above a paged table; row navigates to detail with statement and attributes; version history is a secondary route; relationships panel sits below statement on detail (CAP-BROWSE-UI-RELATIONS). Breadcrumb: client → project → requirement uid.
<<<
COMMENT: >>>
KIND: capability
BASE_UID: CAP-BROWSE-UI-REQS
VERSION_N: 1
priority: 10
iteration: iter-r1
security.catalog_ref: CM-2
security.verification_note: Layout prose added 2026-10-10 seed; shipped PR #26.
in_scope_of_contract: ReqALM product (build)
<<<
RELATIONS:
- TYPE: Parent
  VALUE: SEC-CP
- TYPE: Parent
  VALUE: CAP-BROWSE-UI-REQS
  ROLE: Refines
- TYPE: Parent
  VALUE: C08
  ROLE: Satisfies
- TYPE: Parent
  VALUE: D06
  ROLE: Satisfies
- TYPE: Parent
  VALUE: ARCH-UI
  ROLE: Satisfies
- TYPE: Parent
  VALUE: ARCH-UI-GUARD
  ROLE: Satisfies
- TYPE: Parent
  VALUE: CAP-READ-REQS
  ROLE: Satisfies
- TYPE: Child
  VALUE: CONTRACT-ctr-reqalm-product
  ROLE: InScopeOf

[REQUIREMENT]
UID: CAP-READ-RELEASES
STATUS: Active
TITLE: Read releases (list, detail)
STATEMENT: >>>
Grant-scoped releases read APIs: paged GET /api/v1/projects/:projectId/releases with optional status (planned | shipped), ordered planned_on desc then id; GET detail with notes and delivered capabilities (capability lines from release_delivers). cyber_gate is stored on the release row but not exposed in v1 read DTOs. gate_signoffs and contract in_scope_of edges from dogfood are not loaded by the seed loader (deferred). Invalid release id segments redact in logs/spans like project slugs.
<<<
COMMENT: >>>
KIND: capability
BASE_UID: CAP-READ-RELEASES
VERSION_N: 0
priority: 10
iteration: iter-r1
security.catalog_ref: AC-3
security.verification_note: Shipped with releases read API PR #25 (merge eca9090802c415f78697cc8b9d000f7f7d67a702).
edge: ← satisfies from CAP-BROWSE-UI-RELEASES
edge: ← satisfies from CAP-BROWSE-UI-RELEASES.1
in_scope_of_contract: ReqALM product (build)
delivered_by_release: R1 — releases read API
<<<
RELATIONS:
- TYPE: Parent
  VALUE: SEC-CP
- TYPE: Parent
  VALUE: G08
  ROLE: Satisfies
- TYPE: Parent
  VALUE: ARCH-API-RBAC
  ROLE: Satisfies
- TYPE: Parent
  VALUE: CAP-SVC-OPERATION-ROUTE
  ROLE: Satisfies
- TYPE: Parent
  VALUE: CAP-RBAC
  ROLE: Satisfies
- TYPE: Child
  VALUE: CONTRACT-ctr-reqalm-product
  ROLE: InScopeOf
- TYPE: Child
  VALUE: RELEASE-rel-r1-read-releases
  ROLE: Delivers

[REQUIREMENT]
UID: CAP-BROWSE-UI-RELEASES
STATUS: Draft
TITLE: Browse releases UI (read-only)
STATEMENT: >>>
Read-only /app browse screens for grant-scoped releases within a project: paged list with status filter (planned | shipped, URL-driven), release detail (notes preserving line breaks and delivered capabilities linking to requirement detail). Uses session/CSRF auth; safe DOM text only. Trace links deferred.
<<<
COMMENT: >>>
KIND: capability
BASE_UID: CAP-BROWSE-UI-RELEASES
VERSION_N: 0
priority: 10
iteration: iter-r1
security.catalog_ref: CM-2
security.verification_note: Shipped with releases browse UI PR #27 (merge 0d9623815cd17b405c27172f5ffad1e5ae9d1cfb).
edge: ← refines from CAP-BROWSE-UI-RELEASES.1
delivered_by_release: R1 — browse releases UI (read-only)
<<<
RELATIONS:
- TYPE: Parent
  VALUE: SEC-CP
- TYPE: Parent
  VALUE: C08
  ROLE: Satisfies
- TYPE: Parent
  VALUE: D06
  ROLE: Satisfies
- TYPE: Parent
  VALUE: ARCH-UI
  ROLE: Satisfies
- TYPE: Parent
  VALUE: ARCH-UI-GUARD
  ROLE: Satisfies
- TYPE: Parent
  VALUE: CAP-READ-RELEASES
  ROLE: Satisfies
- TYPE: Child
  VALUE: RELEASE-rel-r1-browse-ui-releases
  ROLE: Delivers

[REQUIREMENT]
UID: CAP-BROWSE-UI-RELEASES.1
STATUS: Active
TITLE: Browse releases UI (read-only)
STATEMENT: >>>
Read-only /app browse screens for grant-scoped releases within a project: paged list with status filter (planned | shipped, URL-driven), release detail (notes preserving line breaks and delivered capabilities linking to requirement detail). Uses session/CSRF auth; safe DOM text only. Trace links deferred. Layout: Project Releases tab — status filter and paged table; row opens release detail with notes and delivered capabilities list linking to requirement/capability detail routes. Breadcrumb includes project name.
<<<
COMMENT: >>>
KIND: capability
BASE_UID: CAP-BROWSE-UI-RELEASES
VERSION_N: 1
priority: 10
iteration: iter-r1
security.catalog_ref: CM-2
security.verification_note: Layout prose added 2026-10-10 seed; shipped PR #27.
in_scope_of_contract: ReqALM product (build)
<<<
RELATIONS:
- TYPE: Parent
  VALUE: SEC-CP
- TYPE: Parent
  VALUE: CAP-BROWSE-UI-RELEASES
  ROLE: Refines
- TYPE: Parent
  VALUE: C08
  ROLE: Satisfies
- TYPE: Parent
  VALUE: D06
  ROLE: Satisfies
- TYPE: Parent
  VALUE: ARCH-UI
  ROLE: Satisfies
- TYPE: Parent
  VALUE: ARCH-UI-GUARD
  ROLE: Satisfies
- TYPE: Parent
  VALUE: CAP-READ-RELEASES
  ROLE: Satisfies
- TYPE: Child
  VALUE: CONTRACT-ctr-reqalm-product
  ROLE: InScopeOf

[REQUIREMENT]
UID: CAP-BROWSE-UI-RELATIONS
STATUS: Draft
TITLE: Browse requirement relationships UI (read-only)
STATEMENT: >>>
Read-only Relationships panel on the requirement detail browse screen: loads GET /api/v1/projects/:projectId/requirements/:id/relations and renders outgoing and incoming links grouped by kind. Requirement peers navigate to detail; catalog conforms_to peers show as non-navigating chips with imprint label; trace_suspect shows needs re-check; restricted peers show a muted stub with no peer id. Empty, loading, and error states included.
<<<
COMMENT: >>>
KIND: capability
BASE_UID: CAP-BROWSE-UI-RELATIONS
VERSION_N: 0
priority: 10
iteration: iter-r1
security.catalog_ref: CM-2
security.verification_note: Shipped with relationships browse UI PR #32 (merge c8272340b67a0e505b63483bd2ef1550accb4635).
edge: ← refines from CAP-BROWSE-UI-RELATIONS.1
delivered_by_release: R1 — browse requirement relationships UI (read-only)
<<<
RELATIONS:
- TYPE: Parent
  VALUE: SEC-CP
- TYPE: Parent
  VALUE: C08
  ROLE: Satisfies
- TYPE: Parent
  VALUE: D06
  ROLE: Satisfies
- TYPE: Parent
  VALUE: ARCH-UI
  ROLE: Satisfies
- TYPE: Parent
  VALUE: ARCH-UI-GUARD
  ROLE: Satisfies
- TYPE: Parent
  VALUE: CAP-RELATIONS-API
  ROLE: Satisfies
- TYPE: Parent
  VALUE: CAP-BROWSE-UI-REQS
  ROLE: Satisfies
- TYPE: Child
  VALUE: RELEASE-rel-r1-browse-ui-relations
  ROLE: Delivers

[REQUIREMENT]
UID: CAP-BROWSE-UI-RELATIONS.1
STATUS: Active
TITLE: Browse requirement relationships UI (read-only)
STATEMENT: >>>
Read-only Relationships panel on the requirement detail browse screen: loads GET /api/v1/projects/:projectId/requirements/:id/relations and renders outgoing and incoming links grouped by kind. Requirement peers navigate to detail; catalog conforms_to peers show as non-navigating chips with imprint label; trace_suspect shows needs re-check; restricted peers show a muted stub with no peer id. Empty, loading, and error states included. Layout: Relationships region on requirement detail — outgoing and incoming groups by kind; requirement peers link to detail; catalog conforms_to peers render as non-navigating chips; restricted peers show muted stub.
<<<
COMMENT: >>>
KIND: capability
BASE_UID: CAP-BROWSE-UI-RELATIONS
VERSION_N: 1
priority: 10
iteration: iter-r1
security.catalog_ref: CM-2
security.verification_note: Layout prose added 2026-10-10 seed; shipped PR #32.
in_scope_of_contract: ReqALM product (build)
<<<
RELATIONS:
- TYPE: Parent
  VALUE: SEC-CP
- TYPE: Parent
  VALUE: CAP-BROWSE-UI-RELATIONS
  ROLE: Refines
- TYPE: Parent
  VALUE: C08
  ROLE: Satisfies
- TYPE: Parent
  VALUE: D06
  ROLE: Satisfies
- TYPE: Parent
  VALUE: ARCH-UI
  ROLE: Satisfies
- TYPE: Parent
  VALUE: ARCH-UI-GUARD
  ROLE: Satisfies
- TYPE: Parent
  VALUE: CAP-RELATIONS-API
  ROLE: Satisfies
- TYPE: Parent
  VALUE: CAP-BROWSE-UI-REQS
  ROLE: Satisfies
- TYPE: Child
  VALUE: CONTRACT-ctr-reqalm-product
  ROLE: InScopeOf

[REQUIREMENT]
UID: CAP-BROWSE-UI-CATALOGS
STATUS: Active
TITLE: Browse catalogs UI (read-only)
STATEMENT: >>>
Read-only /app browse screens for grant-scoped catalogs within a project: catalog list (title, primary imprint, control count), imprint detail with controls grouped by family and conforming-line counts, and control detail (statement + conforming requirement/capability chips). Uses catalogs read API; restricted catalogs follow API 404/redaction. Safe DOM (textContent only); Catalogs project tab in header nav.
<<<
COMMENT: >>>
KIND: capability
BASE_UID: CAP-BROWSE-UI-CATALOGS
VERSION_N: 0
priority: 10
iteration: iter-r1
security.catalog_ref: CM-2
security.verification_note: Shipped with catalogs browse UI PR #41 (merge cbee54e9484d89430b461789052cea296e1669c5).
in_scope_of_contract: ReqALM product (build)
delivered_by_release: R1 — browse catalogs UI (read-only)
<<<
RELATIONS:
- TYPE: Parent
  VALUE: SEC-CP
- TYPE: Parent
  VALUE: CAP-CATALOGS-API
  ROLE: Satisfies
- TYPE: Parent
  VALUE: CAP-BROWSE-UI-REQS
  ROLE: Satisfies
- TYPE: Parent
  VALUE: CAP-UI-HEADER-NAV
  ROLE: Satisfies
- TYPE: Parent
  VALUE: ARCH-UI-GUARD
  ROLE: Satisfies
- TYPE: Child
  VALUE: CONTRACT-ctr-reqalm-product
  ROLE: InScopeOf
- TYPE: Child
  VALUE: RELEASE-rel-r1-browse-ui-catalogs
  ROLE: Delivers

[REQUIREMENT]
UID: CAP-CONTRACTS-LOADER
STATUS: Active
TITLE: Persist contracts from dogfood (migration + loader)
STATEMENT: >>>
Dogfood loader persists contract overlays from dogfood.yaml into Postgres: contracts, contract_scope, and contract_releases (migration 012_contracts_read.sql). Validates in_scope_of version uids and covers_releases release ids; allows cross-project scope lines anchored on the contract project_id. Seed reset deletes contract junction rows before releases (FK-safe). No HTTP read API in this release.
<<<
COMMENT: >>>
KIND: capability
BASE_UID: CAP-CONTRACTS-LOADER
VERSION_N: 0
priority: 10
iteration: iter-r1
security.catalog_ref: AC-3
security.verification_note: Shipped with contracts storage/loader PR #44 (merge a3ebdcdc23d9032eefa4109603e527b4e80d6c77).
in_scope_of_contract: ReqALM product (build)
delivered_by_release: R1 — contracts loader (DB + seed)
<<<
RELATIONS:
- TYPE: Parent
  VALUE: SEC-CP
- TYPE: Parent
  VALUE: F10
  ROLE: Satisfies
- TYPE: Parent
  VALUE: ARCH-CONTRACT.1
  ROLE: Satisfies
- TYPE: Parent
  VALUE: CAP-SVC-OPERATION-ROUTE
  ROLE: Satisfies
- TYPE: Child
  VALUE: CONTRACT-ctr-reqalm-product
  ROLE: InScopeOf
- TYPE: Child
  VALUE: RELEASE-rel-r1-contracts-loader
  ROLE: Delivers

[REQUIREMENT]
UID: CAP-READ-CONTRACTS
STATUS: Active
TITLE: Read contracts (list, detail, scope, releases)
STATEMENT: >>>
Grant-scoped read-only contracts API under /api/v1/projects/:projectId/contracts: paged list with scope and release counts; detail; paged in_scope_of scope lines (uid, base, kind, status, version) with cross-project lines omitted when the caller lacks requirement:read on the line project; covers_releases release summaries. RBAC contract:read mirrors requirement:read roles; missing/forbidden contract access returns 404.
<<<
COMMENT: >>>
KIND: capability
BASE_UID: CAP-READ-CONTRACTS
VERSION_N: 0
priority: 10
iteration: iter-r1
security.catalog_ref: AC-3
security.verification_note: Shipped with contracts read API PR #43 (merge aa7e85631819d45ac04852831ab305d655f1eddd).
edge: ← satisfies from CAP-BROWSE-UI-CONTRACTS
in_scope_of_contract: ReqALM product (build)
delivered_by_release: R1 — contracts read API
<<<
RELATIONS:
- TYPE: Parent
  VALUE: SEC-CP
- TYPE: Parent
  VALUE: F10
  ROLE: Satisfies
- TYPE: Parent
  VALUE: ARCH-CONTRACT.1
  ROLE: Satisfies
- TYPE: Parent
  VALUE: CAP-SVC-OPERATION-ROUTE
  ROLE: Satisfies
- TYPE: Parent
  VALUE: CAP-READ-REQS
  ROLE: Satisfies
- TYPE: Child
  VALUE: CONTRACT-ctr-reqalm-product
  ROLE: InScopeOf
- TYPE: Child
  VALUE: RELEASE-rel-r1-read-contracts
  ROLE: Delivers

[REQUIREMENT]
UID: CAP-BROWSE-UI-CONTRACTS
STATUS: Active
TITLE: Browse contracts UI (read-only)
STATEMENT: >>>
Read-only /app browse screens for grant-scoped contracts within a project: contract list (title, scope and release counts), contract detail with in_scope_of lines linking to requirement/capability detail and covers_releases linking to release detail. Uses contracts read API; restricted/missing contracts follow API 404. Safe DOM (textContent only); Contracts project tab in header nav. Document view and overlap timeline deferred (mockups 02–03; no read API yet).
<<<
COMMENT: >>>
KIND: capability
BASE_UID: CAP-BROWSE-UI-CONTRACTS
VERSION_N: 0
priority: 10
iteration: iter-r1
security.catalog_ref: AC-3
security.verification_note: Shipped with contracts browse UI PR #45 (merge 86d315462b67446e605d6c898c15df2c8066b5d3).
delivered_by_release: R1 — browse contracts UI (read-only)
<<<
RELATIONS:
- TYPE: Parent
  VALUE: SEC-CP
- TYPE: Parent
  VALUE: CAP-READ-CONTRACTS
  ROLE: Satisfies
- TYPE: Parent
  VALUE: CAP-BROWSE-UI-REQS
  ROLE: Satisfies
- TYPE: Parent
  VALUE: CAP-UI-HEADER-NAV
  ROLE: Satisfies
- TYPE: Parent
  VALUE: CAP-CONTRACT-UI
  ROLE: Satisfies
- TYPE: Parent
  VALUE: ARCH-UI-GUARD
  ROLE: Satisfies
- TYPE: Child
  VALUE: RELEASE-rel-r1-browse-ui-contracts
  ROLE: Delivers

[REQUIREMENT]
UID: CAP-READ-PLANNING
STATUS: Draft
TITLE: planning read API
STATEMENT: >>>
Planning read API (grant-scoped GET routes for backlog / iteration / work-item views). Not implemented in this release; capability statement will tighten when the feature PR lands.
<<<
COMMENT: >>>
KIND: capability
BASE_UID: CAP-READ-PLANNING
VERSION_N: 0
priority: 10
iteration: iter-r1
security.catalog_ref: AC-3
security.verification_note: Started 2026-10-10 (cloud agent bc-a71c6948); not shipped.
delivered_by_release: R1 — planning read API
<<<
RELATIONS:
- TYPE: Parent
  VALUE: SEC-CP
- TYPE: Parent
  VALUE: ARCH-BROWSE-ROADMAP
  ROLE: Satisfies
- TYPE: Parent
  VALUE: ARCH-PLANNING-GATES
  ROLE: Satisfies
- TYPE: Child
  VALUE: RELEASE-rel-r1-planning-read-api
  ROLE: Delivers

[REQUIREMENT]
UID: CAP-READ-ARTIFACTS
STATUS: Draft
TITLE: capability artifacts read API
STATEMENT: >>>
Read API for capability_artifacts (list/detail by requirement version). Not implemented in this release; honest placeholder until artifacts read PR merges.
<<<
COMMENT: >>>
KIND: capability
BASE_UID: CAP-READ-ARTIFACTS
VERSION_N: 0
priority: 10
iteration: iter-r1
security.catalog_ref: AC-3
security.verification_note: Started 2026-10-10 (cloud agent bc-72846206); not shipped.
delivered_by_release: R1 — capability artifacts read API
<<<
RELATIONS:
- TYPE: Parent
  VALUE: SEC-CP
- TYPE: Parent
  VALUE: ARCH-ATTACH-PIN-VERSION
  ROLE: Satisfies
- TYPE: Parent
  VALUE: CAP-ATTACH-READ
  ROLE: Refines
- TYPE: Child
  VALUE: RELEASE-rel-r1-artifacts-read-api
  ROLE: Delivers

[REQUIREMENT]
UID: CAP-SVC-HARDENING-FOLLOWUP
STATUS: Draft
TITLE: hardening follow-up (no-project gate, fetchAllScope, test kit)
STATEMENT: >>>
Follow-up hardening after RBAC fail-closed: explicit !projectId gate on routes that must not infer scope, bound fetchAllScope pagination in browse test kits, and rename shared contract browse test helpers for clarity. Work in progress on cloud agent; not shipped.
<<<
COMMENT: >>>
KIND: capability
BASE_UID: CAP-SVC-HARDENING-FOLLOWUP
VERSION_N: 0
priority: 10
iteration: iter-r1
security.catalog_ref: AC-3
security.verification_note: Started 2026-10-10 (cloud agent bc-7132b537); not shipped.
delivered_by_release: R1 — hardening follow-up (no-project gate, fetchAllScope, test kit)
<<<
RELATIONS:
- TYPE: Parent
  VALUE: SEC-CP
- TYPE: Parent
  VALUE: ARCH-API-RBAC
  ROLE: Satisfies
- TYPE: Parent
  VALUE: CAP-SVC-RBAC-NO-PROJECT
  ROLE: Refines
- TYPE: Child
  VALUE: RELEASE-rel-r1-hardening-followup-1
  ROLE: Delivers

[[/SECTION]]

[[SECTION]]
UID: SEC-RL
TITLE: Requirement Lines & Versions

[TEXT]
UID: SEC-RL-INTRO
STATEMENT: >>>
Requirement lines are stable tree nodes; requirement versions hold statement and status. Tree edit, version succession, and lineage viewing live here.
<<<

[REQUIREMENT]
UID: C01
STATUS: Active
TITLE: Create requirement line
STATEMENT: >>>
An Author creates a section, requirement, control, or capability line under a parent line (or as a root
section). ReqAML inserts a requirement_line with stable base_uid, kind, and title; parent is always a line
base_uid (or null). Creating a line does not create a version until the author adds first content (D01).
<<<
COMMENT: >>>
KIND: requirement
BASE_UID: C01
VERSION_N: 0
rbac_op: requirement:line:create
priority: 10
iteration: iter-r0
security.catalog_ref: AC-3
security.verification_note: AC-3 access enforcement; AU-2/3/12 where mutating.
edge: ← satisfies from CAP-TREE
edge: ← refines from ARCH-HIER-REQ-DECOMP
in_scope_of_contract: Design-2026-10
in_scope_of_contract: Platform baseline
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r1-core-alm
  ROLE: Delivers

[REQUIREMENT]
UID: C02
STATUS: Active
TITLE: Rename / retitle line
STATEMENT: >>>
An Author renames a line's title. ReqAML updates the line title only; version statements and UIDs are
unchanged. The rename is audited with actor and before/after title.
<<<
COMMENT: >>>
KIND: requirement
BASE_UID: C02
VERSION_N: 0
rbac_op: requirement:line:retitle
priority: 35
iteration: iter-r0
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: C03
STATUS: Active
TITLE: Move line (change parent)
STATEMENT: >>>
An Author moves a line to a new parent within the same project. ReqAML updates parent to the target
line base_uid, rejects cycles, and does not cascade-fork versions of ancestors or descendants.
Contracts and releases that reference version UIDs remain valid.
<<<
COMMENT: >>>
KIND: requirement
BASE_UID: C03
VERSION_N: 0
rbac_op: requirement:line:move
priority: 30
iteration: iter-r1
security.catalog_ref: AC-3
security.verification_note: AC-3 access enforcement; AU-2/3/12 where mutating.
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: ARCH-VER
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: C04
STATUS: Active
TITLE: Reorder siblings
STATEMENT: >>>
An Author reorders sibling lines under the same parent. ReqAML persists sibling order for outline and
mind-map rendering without changing parent pointers or version content.
<<<
COMMENT: >>>
KIND: requirement
BASE_UID: C04
VERSION_N: 0
rbac_op: requirement:line:reorder
priority: 45
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: C05
STATUS: Active
TITLE: Soft-delete / tombstone line
STATEMENT: >>>
An Author soft-deletes a line via the obsolete-version flow (D05) rather than hard-deleting rows.
ReqAML marks the latest content obsolete/withdrawn as a new version and hides the line from default tree
views while retaining lineage for auditors.
<<<
COMMENT: >>>
KIND: requirement
BASE_UID: C05
VERSION_N: 0
rbac_op: requirement:line:tombstone
priority: 50
iteration: iter-r1
security.catalog_ref: AC-3
security.verification_note: AC-3 access enforcement; AU-2/3/12 where mutating.
edge: ← refines from ARCH-ATTACH
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: ARCH-VER-TOMB
  ROLE: Refines
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: C06
STATUS: Active
TITLE: View tree (mind map / outline)
STATEMENT: >>>
A Reader views the requirement tree as outline or mind map for the scoped project. ReqAML returns
line hierarchy with current active (or draft) version summaries; obsolete lines are filtered unless requested.
<<<
COMMENT: >>>
KIND: requirement
BASE_UID: C06
VERSION_N: 0
rbac_op: requirement:tree:read
priority: 15
iteration: iter-r0
security.catalog_ref: AC-3
security.verification_note: AC-3 access enforcement; AU-2/3/12 where mutating.
edge: ← satisfies from CAP-TREE
edge: ← uses from N01
edge: ← satisfies from CAP-READ-HIERARCHY
edge: ← satisfies from CAP-BROWSE-UI-TREE
edge: ← satisfies from CAP-BROWSE-UI-TREE.1
in_scope_of_contract: Design-2026-10
in_scope_of_contract: Platform baseline
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r1-core-alm
  ROLE: Delivers

[REQUIREMENT]
UID: C07
STATUS: Active
TITLE: Expand / collapse / filter tree
STATEMENT: >>>
A Reader expands, collapses, or filters the tree by kind, status, text, or approval state. Filtering is a view concern; it does not mutate lines. Filters honor Scoped View and RBAC so unauthorized lines never appear. Approval filter (ARCH-APPROVAL-VIEW) shows unapproved versions as the primary tree; approved ones are dimmed/collapsed — same pattern as other filtered trees (status/kind).
<<<
COMMENT: >>>
KIND: requirement
BASE_UID: C07
VERSION_N: 0
rbac_op: requirement:tree:filter
priority: 40
iteration: iter-r0
security.catalog_ref: AC-3
security.verification_note: AC-3 access enforcement; AU-2/3/12 where mutating.
edge: ← satisfies from CAP-READ-HIERARCHY
edge: ← satisfies from CAP-UI-KIT
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: C08
STATUS: Active
TITLE: Search requirements in client/project
STATEMENT: >>>
A Reader searches requirement statements and titles within the scoped client/project. ReqAML returns
matching version UIDs with snippets; search never crosses clients even if the caller has multi-client grants.
<<<
COMMENT: >>>
KIND: requirement
BASE_UID: C08
VERSION_N: 0
rbac_op: requirement:search
priority: 20
iteration: iter-r1
security.catalog_ref: AC-3
security.verification_note: AC-3 access enforcement; AU-2/3/12 where mutating.
edge: ← satisfies from CAP-TREE
edge: ← uses from N03
edge: ← satisfies from CAP-READ-REQS
edge: ← satisfies from CAP-BROWSE-UI-REQS
edge: ← satisfies from CAP-BROWSE-UI-RELEASES
edge: ← satisfies from CAP-RELATIONS-API
edge: ← satisfies from CAP-CATALOGS-API
edge: ← satisfies from CAP-BROWSE-UI-RELATIONS
edge: ← satisfies from CAP-BROWSE-UI-REQS.1
edge: ← satisfies from CAP-BROWSE-UI-RELEASES.1
edge: ← satisfies from CAP-BROWSE-UI-RELATIONS.1
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: D01
STATUS: Active
TITLE: Create first version of a line
STATEMENT: >>>
An Author creates the first requirement_version for a line (version_n 0, uid = base_uid). ReqAML stores
statement, status (typically draft), and optional priority/iteration/rbac_op/security metadata.
No in-place overwrite of a published version is allowed afterward — successors use .N.
<<<
COMMENT: >>>
KIND: requirement
BASE_UID: D01
VERSION_N: 0
rbac_op: requirement:version:create
priority: 10
iteration: iter-r0
security.catalog_ref: AC-3
security.verification_note: AC-3 access enforcement; AU-2/3/12 where mutating.
in_scope_of_contract: Design-2026-10
in_scope_of_contract: Platform baseline
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r1-core-alm
  ROLE: Delivers

[REQUIREMENT]
UID: D02
STATUS: Active
TITLE: Create successor version (.N+1)
STATEMENT: >>>
An Author creates a successor version with version_n = prior+1 and uid base_uid.N. ReqAML copies or
drafts new statement content; prior versions remain immutable rows. Children stay on the parent line
(parent = base_uid); there is no cascade fork.
<<<
COMMENT: >>>
KIND: requirement
BASE_UID: D02
VERSION_N: 0
rbac_op: requirement:version:succeed
priority: 10
iteration: iter-r0
security.catalog_ref: AC-3
security.verification_note: AC-3 access enforcement; AU-2/3/12 where mutating.
edge: ← satisfies from CAP-VERSION-UI
edge: ← uses from FIX-ALLOW-SUCCEED
in_scope_of_contract: Design-2026-10
in_scope_of_contract: Platform baseline
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: ARCH-VER-SUCC
  ROLE: Refines
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r1-core-alm
  ROLE: Delivers

[REQUIREMENT]
UID: D03
STATUS: Active
TITLE: Edit draft version fields
STATEMENT: >>>
An Author edits fields on a draft version (statement, metadata). ReqAML allows mutation only while
status is draft; active/obsolete/withdrawn rows are immutable and require a successor for changes
(FIX-DENY-EDIT-ACTIVE, CM-3). Draft updates are audited.
<<<
COMMENT: >>>
KIND: requirement
BASE_UID: D03
VERSION_N: 0
rbac_op: requirement:version:update_draft
priority: 15
iteration: iter-r0
security.catalog_ref: AC-3
security.verification_note: AC-3 access enforcement; AU-2/3/12 where mutating.
edge: ← uses from MC02
edge: ← uses from FIX-DENY-EDIT-ACTIVE
in_scope_of_contract: Design-2026-10
in_scope_of_contract: Platform baseline
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r1-core-alm
  ROLE: Delivers

[REQUIREMENT]
UID: D04
STATUS: Active
TITLE: Activate draft→active; prior active→superseded in-place (≠ approve)
STATEMENT: >>>
An Author or Project admin marks a draft version active (lifecycle status only). ReqAML transitions status to active and, in the SAME transaction, sets any prior active version of the same line to superseded IN PLACE (not a new version) so the ≤1-active invariant holds (ARCH-VER / FIX-DENY-SECOND-ACTIVE). Activation is audited. IMPORTANT: activate (D04) is NOT stakeholder approval — approval is ApprovalRecord on the line (ARCH-APPROVAL-LINE / D12). An active but unapproved / planning_blocked line cannot receive priority mutate (D08).
<<<
COMMENT: >>>
KIND: requirement
BASE_UID: D04
VERSION_N: 0
rbac_op: requirement:version:activate
priority: 20
iteration: iter-r0
security.catalog_ref: AC-3
security.verification_note: AC-3 access enforcement; AU-2/3/12 where mutating.
edge: ← uses from J02
in_scope_of_contract: Design-2026-10
in_scope_of_contract: Platform baseline
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r1-core-alm
  ROLE: Delivers

[REQUIREMENT]
UID: D05
STATUS: Active
TITLE: Terminal obsolete/withdraw in-place or status-only .N
STATEMENT: >>>
An Author marks content obsolete or withdrawn. Terminal obsolete/withdraw WITHOUT a replacement tip is an in-place status change on the current tip (or a status-only .N with mint_kind=status, exempt from content no-op and NOT clearing ApprovalRecord). When a replacement tip exists, the prior tip becomes superseded via D04 activate — not a separate obsolete successor required for every replacement. Tombstoned lines disappear from default tree views. Soft-delete remains auditable (ARCH-VER-TOMB / AU-12).
<<<
COMMENT: >>>
KIND: requirement
BASE_UID: D05
VERSION_N: 0
rbac_op: requirement:version:obsolete
priority: 35
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: ARCH-VER-TOMB
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: D06
STATUS: Active
TITLE: View lineage / succession
STATEMENT: >>>
A Reader views lineage for a UID — all version_n rows for the base_uid with statuses and timestamps.
The lineage view supports navigation used by mockup 04 (requirement lineage / versions).
<<<
COMMENT: >>>
KIND: requirement
BASE_UID: D06
VERSION_N: 0
rbac_op: requirement:version:lineage
priority: 25
iteration: iter-r0
security.catalog_ref: AC-3
security.verification_note: AC-3 access enforcement; AU-2/3/12 where mutating.
edge: ← satisfies from CAP-VERSION-UI
edge: ← satisfies from CAP-READ-REQS
edge: ← satisfies from CAP-BROWSE-UI-REQS
edge: ← satisfies from CAP-BROWSE-UI-RELEASES
edge: ← satisfies from CAP-BROWSE-UI-RELATIONS
edge: ← satisfies from CAP-BROWSE-UI-REQS.1
edge: ← satisfies from CAP-BROWSE-UI-RELEASES.1
edge: ← satisfies from CAP-BROWSE-UI-RELATIONS.1
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: D07
STATUS: Active
TITLE: Compare two versions
STATEMENT: >>>
A Reader compares two versions of the same or related UIDs. ReqAML returns a field-level diff of
statement and metadata. Multi-hop lineages (FIX-SUCC-2HOP) are supported so .0 vs .2 compares remain
meaningful for QA (FIX-COMPARE-2HOP).
<<<
COMMENT: >>>
KIND: requirement
BASE_UID: D07
VERSION_N: 0
rbac_op: requirement:version:compare
priority: 40
iteration: iter-r1
security.catalog_ref: AC-3
security.verification_note: AC-3 access enforcement; AU-2/3/12 where mutating.
edge: ← satisfies from CAP-VERSION-UI
edge: ← uses from FIX-COMPARE-2HOP
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: D08
STATUS: Active
TITLE: Priority mutate requires approved + not planning_blocked
STATEMENT: >>>
An Author sets or clears integer priority on a version ONLY when the line's ApprovalRecord.status is approved (or imported_approved per FIX-GRANDFATHER-SEED-APPROVED) AND planning_blocked is false (ARCH-APPROVAL-LINE / gate-line-approved). After a content .N clears approval, priority/grooming/iteration VALUES are retained but D08 mutate is DENIED while planning_blocked (FIX-PLANNING-BLOCKED-AFTER-CONTENT-N). Contract/release membership is not auto-dropped — marked suspect. Setting priority on an unapproved/blocked line denies (FIX-DENY-PRIORITY-UNAPPROVED). Activate (D04) alone does not unlock priority.
<<<
COMMENT: >>>
KIND: requirement
BASE_UID: D08
VERSION_N: 0
rbac_op: requirement:version:priority
priority: 30
iteration: iter-r1
security.catalog_ref: AC-3
security.verification_note: AC-3 access enforcement; AU-2/3/12 where mutating.
edge: ← uses from K01
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: D09
STATUS: Active
TITLE: Attach / change iteration on a version
STATEMENT: >>>
An Author attaches or changes the iteration (sprint window) on a version. ReqAML validates the iteration
belongs to the same project and audits the assignment for work-track views.
<<<
COMMENT: >>>
KIND: requirement
BASE_UID: D09
VERSION_N: 0
rbac_op: requirement:version:iteration
priority: 30
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: D10
STATUS: Active
TITLE: Add verification note (tester)
STATEMENT: >>>
A Tester adds or updates a verification_note on a version's security metadata (or adjacent test note field). The Tester also sets first-class verification_outcome (pass|fail|pending) on the version (ARCH-VERIFICATION). ReqAML records the tester identity and timestamp; Authors cannot silently overwrite tester notes without audit. Whether verification_outcome blocks G05 ship is determined by WorkflowProfile Gate gate-verification-ship (ARCH-VERIFICATION-GATE) — configurable, not permanently soft.
<<<
COMMENT: >>>
KIND: requirement
BASE_UID: D10
VERSION_N: 0
rbac_op: requirement:version:verification_note
priority: 45
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: D11
STATUS: Active
TITLE: Tag security metadata
STATEMENT: >>>
A Security reviewer tags catalog_ref and verification guidance on a version. ReqAML stores security
metadata alongside the statement so NIST/STIG alignment travels with the requirement version UID.
<<<
COMMENT: >>>
KIND: requirement
BASE_UID: D11
VERSION_N: 0
rbac_op: requirement:version:security_tag
priority: 35
iteration: iter-r1
security.catalog_ref: AC-3
security.verification_note: Security tagging itself is an audited mutating op.
edge: ← uses from H06
in_scope_of_contract: Security package
in_scope_of_contract: ReqALM product (build)
edge: → conforms_to to AC-3 (pin imprint=nist-800-53@rev5-dogfood-20261006)
<<<
RELATIONS:
- TYPE: Parent
  VALUE: SEC-RL
- TYPE: Parent
  VALUE: AC-3
  ROLE: ConformsTo
- TYPE: Child
  VALUE: CONTRACT-contract-security-package
  ROLE: InScopeOf
- TYPE: Child
  VALUE: CONTRACT-ctr-reqalm-product
  ROLE: InScopeOf

[REQUIREMENT]
UID: ARCH-VER
STATUS: Active
TITLE: Line versions; ≤1 active; prior→superseded in-place on activate
STATEMENT: >>>
Each requirement line has versions with UIDs base_uid or base_uid.N (static append). Children stay on the parent line (parent = base_uid); there is no cascade fork. INVARIANT: ≤1 active version per line. When a new tip is activated (D04), the prior active version is set to superseded IN PLACE in the same transaction (not a new version). Terminal obsolete/withdraw without replacement may be in-place status or a status-only .N (mint_kind=status) — see D05 / ARCH-MINT-KIND / FIX-ALLOW-STATUS-SUPERSEDE.
<<<
COMMENT: >>>
KIND: requirement
BASE_UID: ARCH-VER
VERSION_N: 0
priority: 5
iteration: iter-r0
security.catalog_ref: AC-3
security.verification_note: AC-3 access enforcement; AU-2/3/12 where mutating.
edge: ← uses from ARCH-API
edge: ← uses from C03
edge: ← uses from FIX-ALLOW-STATUS-SUPERSEDE
edge: ← refines from ARCH-WRITE-VERSION-UNIQUE
in_scope_of_contract: Design-2026-10
in_scope_of_contract: Platform baseline
in_scope_of_contract: ReqALM product (build)
delivered_by_release: R0-sequences
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-RL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r0-sequences
  ROLE: Delivers

[[SECTION]]
UID: ARCH-VER-CHILDREN
TITLE: Children of ARCH-VER

[REQUIREMENT]
UID: ARCH-VER-SUCC
STATUS: Active
TITLE: Succession UID rules; ≤1 active invariant; supersede same txn
STATEMENT: >>>
Succession always increments version_n. uid for version_n 0 is base_uid (or base_uid.0); for n>0 uid is base_uid.n. Published (active) statement rows are immutable for content; content edits require a new successor (mint_kind=content). Exactly one active version per line is an INVARIANT (FIX-DENY-SECOND-ACTIVE). On activate of a new tip, prior active → superseded in-place same txn (FIX-ALLOW-SUCCEED).
<<<
COMMENT: >>>
KIND: requirement
BASE_UID: ARCH-VER-SUCC
VERSION_N: 0
priority: 5
iteration: iter-r0
security.catalog_ref: AC-3
security.verification_note: AC-3 access enforcement; AU-2/3/12 where mutating.
edge: ← refines from D02
edge: ← refines from FIX-SUCC-2HOP.2
edge: ← uses from ARCH-CAT-REACT
edge: ← uses from ARCH-CAT-MIGRATE
edge: ← uses from FIX-DENY-SECOND-ACTIVE
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: ARCH-VER
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: ARCH-VER-TOMB
STATUS: Active
TITLE: Tombstone via obsolete version
STATEMENT: >>>
Soft-delete of a line is expressed by obsolete or withdrawn status (in-place terminal, or status-only .N) — not by deleting requirement_line rows. When replaced by a newer tip, prior active becomes superseded in-place (D04). Historical contracts and releases that delivered prior UIDs remain coherent (may be marked trace_suspect). Succession and tombstone events are auditable (AU-12).
<<<
COMMENT: >>>
KIND: requirement
BASE_UID: ARCH-VER-TOMB
VERSION_N: 0
priority: 15
iteration: iter-r1
security.catalog_ref: AU-12
security.verification_note: Tombstone/obsolete path generates auditable succession (AU-12).
edge: ← refines from C05
edge: ← uses from D05
in_scope_of_contract: ReqALM product (build)
edge: → conforms_to to AU-12 (pin imprint=nist-800-53@rev5-dogfood-20261006)
<<<
RELATIONS:
- TYPE: Parent
  VALUE: ARCH-VER
- TYPE: Parent
  VALUE: AU-12
  ROLE: ConformsTo
- TYPE: Child
  VALUE: CONTRACT-ctr-reqalm-product
  ROLE: InScopeOf

[[/SECTION]]

[REQUIREMENT]
UID: D12
STATUS: Active
TITLE: Stakeholder Approve (line + direct children)
STATEMENT: >>>
An actor matching the WorkflowProfile RoleBinding for the stakeholder (or solution_approver) slot approves a requirement or capability LINE — not a hard-coded Client admin vs AO. Approve (UI-APPROVE-LINE / requirement:line:approve) writes ApprovalRecord(s) for the selected line AND its direct children, pinning approved_version_uid and approved_statement_hash for each. Approval is separate from lifecycle status (draft/active/obsolete). Activate (D04) ≠ approve. Unapproved lines appear in the approval tree (ARCH-APPROVAL-VIEW); approved ones are dimmed/collapsed. Priority and other profile-selected planning actions require line approved (ARCH-PLANNING-GATES). Version.stakeholder_approval is a denormalized mirror during migrate (dual-write); do not treat it as SoT. Re-approve after content .N clears planning_blocked (FIX-PLANNING-BLOCKED-AFTER-CONTENT-N). Approve hooks evaluate gate-approver-slot (FIX-DENY-APPROVE-WITHOUT-SLOT / FIX-ALLOW-APPROVE-LINE).
<<<
COMMENT: >>>
KIND: requirement
BASE_UID: D12
VERSION_N: 0
rbac_op: requirement:line:approve
priority: 15
iteration: iter-r1
security.catalog_ref: AC-3
security.verification_note: Approver = RoleBinding slot (profile-configurable). AC-3/AU-2/3/12.
edge: ← uses from FIX-DENY-APPROVE-WITHOUT-SLOT
edge: ← uses from FIX-ALLOW-APPROVE-LINE
edge: ← refines from ARCH-CRED-REAUTH
edge: ← uses from FIX-DENY-STEPUP-STALE-AUTH
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-RL
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: ARCH-APPROVAL
STATUS: Active
TITLE: ApprovalRecord on line (SoT); version mirror dual-write
STATEMENT: >>>
Stakeholder / solution approval SoT is ApprovalRecord on the line (subject_kind RequirementLine or CapabilityLine; status unapproved|approved; by, at, notes; approved_version_uid; approved_statement_hash) — NOT a lifecycle status and NOT version-only. D04 activate remains draft→active only. D08 and other profile-gated planning actions read ApprovalRecord on the line (ARCH-APPROVAL-LINE). Approver roles come from RoleBinding on the WorkflowProfile (ARCH-APPROVER-SLOTS) — never hard-coded Client admin vs AO in the engine. Dogfood commercial profile binds stakeholder → Client admin; DoD example profile may bind AO / Project admin. During migrate, requirement_version.stakeholder_approval may dual-write as a mirror; clearing and gate evaluation always use the line ApprovalRecord + hash.
<<<
COMMENT: >>>
KIND: requirement
BASE_UID: ARCH-APPROVAL
VERSION_N: 0
priority: 15
iteration: iter-r0
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-RL
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: ARCH-VERIFICATION
STATUS: Active
TITLE: verification_outcome first-class; configurable ship gate
STATEMENT: >>>
verification_outcome on requirement_version is first-class (pass | fail | pending), set by Tester (D10). It complements verification_note without inventing a full evidence CMS. Ship may be gated by Gate gate-verification-ship under WorkflowProfile when the profile enables it (ARCH-VERIFICATION-GATE / ARCH-GATE-MODEL) — not soft-only dismiss. Commercial default leaves gate-verification-ship disabled; DoD/cyber example profile may enable it. Cyber gate and stakeholder approval do not automatically imply verification pass.
<<<
COMMENT: >>>
KIND: requirement
BASE_UID: ARCH-VERIFICATION
VERSION_N: 0
rbac_op: requirement:version:verification_outcome
priority: 25
iteration: iter-r1
security.catalog_ref: AC-3
security.verification_note: Soft/v1 verification_outcome; Tester sets. Does not block ship unless future policy.
edge: ← refines from ARCH-REQ-AC-FACET
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-RL
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: D13
STATUS: Active
TITLE: Stakeholder Approve Tree (full descendants) on requirement lines
STATEMENT: >>>
An actor matching the stakeholder (or bound) RoleBinding performs Approve Tree on a requirement or capability line: writes ApprovalRecord for the line and every descendant, pinning each approved_version_uid + approved_statement_hash. Same activate≠approve and mirror dual-write rules as D12. Use when signing off a whole section/subtree; use D12/UI-APPROVE-LINE for line+direct children only.
<<<
COMMENT: >>>
KIND: requirement
BASE_UID: D13
VERSION_N: 0
rbac_op: requirement:line:approve_tree
priority: 15
iteration: iter-r1
security.catalog_ref: AC-3
security.verification_note: AC-3 access enforcement; AU-2/3/12 where mutating.
edge: ← refines from ARCH-CRED-REAUTH
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-RL
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: CAP-READ-HIERARCHY
STATUS: Active
TITLE: Read requirement hierarchy (lazy tree API)
STATEMENT: >>>
Grant-scoped requirement hierarchy read API: lazy paged GET /api/v1/projects/:projectId/requirements/tree?parent=<base_uid> returning direct children in dogfood sibling order with uid, title, kind, type, status, and child_count (sections and requirements alike; roots = parent null). Optional parent_uid and ancestors on detail. Parent pointers already live on requirement_lines (001); loader adds sibling_order and rejects cross-project parents. Trace edges and obsolete-line filtering are deferred.
<<<
COMMENT: >>>
KIND: capability
BASE_UID: CAP-READ-HIERARCHY
VERSION_N: 0
priority: 10
iteration: iter-r1
security.catalog_ref: AC-3
security.verification_note: Shipped with requirement hierarchy read API PR #28 (merge ffd1d5c38ffc6f09c13dd877c82bf0d4bd891764).
edge: ← satisfies from CAP-BROWSE-UI-TREE
edge: ← satisfies from CAP-BROWSE-UI-TREE.1
in_scope_of_contract: ReqALM product (build)
delivered_by_release: R1 — requirement hierarchy read API
<<<
RELATIONS:
- TYPE: Parent
  VALUE: SEC-RL
- TYPE: Parent
  VALUE: C06
  ROLE: Satisfies
- TYPE: Parent
  VALUE: C07
  ROLE: Satisfies
- TYPE: Parent
  VALUE: ARCH-API-RBAC
  ROLE: Satisfies
- TYPE: Parent
  VALUE: CAP-READ-REQS
  ROLE: Satisfies
- TYPE: Parent
  VALUE: CAP-SVC-OPERATION-ROUTE
  ROLE: Satisfies
- TYPE: Parent
  VALUE: CAP-RBAC
  ROLE: Satisfies
- TYPE: Child
  VALUE: CONTRACT-ctr-reqalm-product
  ROLE: InScopeOf
- TYPE: Child
  VALUE: RELEASE-rel-r1-read-hierarchy
  ROLE: Delivers

[REQUIREMENT]
UID: CAP-BROWSE-UI-TREE
STATUS: Draft
TITLE: Browse requirements tree UI (read-only)
STATEMENT: >>>
Read-only /app requirements tree for a grant-scoped project: lazy-loaded outline at /app/projects/:projectId/tree using GET .../requirements/tree?parent= (roots when omitted). Each node shows kind, uid, title; expanders load children once and cache in memory. Accessible WAI-ARIA tree (roles, aria-expanded/level, keyboard navigation). Requirement detail breadcrumbs from ancestors (sections link to tree). Session/CSRF auth; safe DOM text only.
<<<
COMMENT: >>>
KIND: capability
BASE_UID: CAP-BROWSE-UI-TREE
VERSION_N: 0
priority: 10
iteration: iter-r1
security.catalog_ref: CM-2
security.verification_note: Shipped with requirements tree browse UI PR #29 (merge ecf5d539cdcb7da35c9469b7e8e5794240de44f9).
edge: ← refines from CAP-BROWSE-UI-TREE.1
delivered_by_release: R1 — browse requirements tree UI (read-only)
<<<
RELATIONS:
- TYPE: Parent
  VALUE: SEC-RL
- TYPE: Parent
  VALUE: C06
  ROLE: Satisfies
- TYPE: Parent
  VALUE: ARCH-UI
  ROLE: Satisfies
- TYPE: Parent
  VALUE: ARCH-UI-GUARD
  ROLE: Satisfies
- TYPE: Parent
  VALUE: CAP-READ-HIERARCHY
  ROLE: Satisfies
- TYPE: Parent
  VALUE: CAP-UI-KIT-TREE
  ROLE: Uses
- TYPE: Child
  VALUE: RELEASE-rel-r1-browse-ui-tree
  ROLE: Delivers

[REQUIREMENT]
UID: CAP-BROWSE-UI-TREE.1
STATUS: Active
TITLE: Browse requirements tree UI (read-only)
STATEMENT: >>>
Read-only /app requirements tree for a grant-scoped project: lazy-loaded outline at /app/projects/:projectId/tree using GET .../requirements/tree?parent= (roots when omitted). Each node shows kind, uid, title; expanders load children once and cache in memory. Accessible WAI-ARIA tree (roles, aria-expanded/level, keyboard navigation). Requirement detail breadcrumbs from ancestors (sections link to tree). Session/CSRF auth; safe DOM text only. Layout: Project Requirements tree mode — lazy tree in the primary column (see also repo mockup 01-requirements-tree-detail.jpg); selecting a requirement navigates to the requirement detail route (no split-pane detail on the tree URL). Section ancestors in breadcrumb on detail link back to tree parent. List/tree toggle lives in the header tab strip.
<<<
COMMENT: >>>
KIND: capability
BASE_UID: CAP-BROWSE-UI-TREE
VERSION_N: 1
priority: 10
iteration: iter-r1
security.catalog_ref: CM-2
security.verification_note: Layout prose added 2026-10-10 seed; shipped PR #29.
in_scope_of_contract: ReqALM product (build)
<<<
RELATIONS:
- TYPE: Parent
  VALUE: SEC-RL
- TYPE: Parent
  VALUE: CAP-BROWSE-UI-TREE
  ROLE: Refines
- TYPE: Parent
  VALUE: C06
  ROLE: Satisfies
- TYPE: Parent
  VALUE: ARCH-UI
  ROLE: Satisfies
- TYPE: Parent
  VALUE: ARCH-UI-GUARD
  ROLE: Satisfies
- TYPE: Parent
  VALUE: CAP-READ-HIERARCHY
  ROLE: Satisfies
- TYPE: Parent
  VALUE: CAP-UI-KIT-TREE
  ROLE: Uses
- TYPE: Child
  VALUE: CONTRACT-ctr-reqalm-product
  ROLE: InScopeOf

[REQUIREMENT]
UID: ARCH-REQ-AC-FACET
STATUS: Active
TITLE: Acceptance criteria facets
STATEMENT: >>>
An acceptance criterion (facet) is a verifiable condition attached to exactly one requirement version — not a separate requirement line and not a capability line. Facets shall have no independent trace graph; satisfaction is recorded on the parent requirement. Each facet shall use a testable 'shall' statement. A child requirement line (decomposition) is a distinct concept per ARCH-HIER-REQ-DECOMP.
<<<
COMMENT: >>>
KIND: requirement
BASE_UID: ARCH-REQ-AC-FACET
VERSION_N: 0
rbac_op: requirement:tree:read
priority: 15
iteration: iter-r1
security.catalog_ref: CM-2
security.verification_note: Groomed 2026-10-09; pre-write or UI track.
edge: ← refines from ARCH-REQ-AC-ROLLUP
edge: ← satisfies from CAP-UI-VIEW-CRITERIA
in_scope_of_contract: ReqALM product (build)
<<<
RELATIONS:
- TYPE: Parent
  VALUE: SEC-RL
- TYPE: Parent
  VALUE: ARCH-VERIFICATION
  ROLE: Refines
- TYPE: Child
  VALUE: CONTRACT-ctr-reqalm-product
  ROLE: InScopeOf

[REQUIREMENT]
UID: ARCH-REQ-AC-ROLLUP
STATUS: Active
TITLE: Roll up completeness from facets
STATEMENT: >>>
Requirement completeness shall roll up from acceptance criteria on the parent version: the parent is complete when every attached facet is satisfied; a facet is satisfied when at least one linked capability (or verified implementation) satisfies it. Partial facet satisfaction shall surface as incomplete on the parent.
<<<
COMMENT: >>>
KIND: requirement
BASE_UID: ARCH-REQ-AC-ROLLUP
VERSION_N: 0
rbac_op: requirement:tree:read
priority: 15
iteration: iter-r1
security.catalog_ref: CM-2
security.verification_note: Groomed 2026-10-09; pre-write or UI track.
edge: ← satisfies from CAP-UI-VIEW-CRITERIA
in_scope_of_contract: ReqALM product (build)
<<<
RELATIONS:
- TYPE: Parent
  VALUE: SEC-RL
- TYPE: Parent
  VALUE: ARCH-REQ-AC-FACET
  ROLE: Refines
- TYPE: Child
  VALUE: CONTRACT-ctr-reqalm-product
  ROLE: InScopeOf

[[/SECTION]]

[[SECTION]]
UID: SEC-EDGE
TITLE: Traces & Edges

[TEXT]
UID: SEC-EDGE-INTRO
STATEMENT: >>>
Traceability edges connect requirement versions (refines, conforms_to, uses, satisfies). Graph/matrix navigation and edge lifecycle live here.
<<<

[REQUIREMENT]
UID: E01
STATUS: Active
TITLE: Add edge refines
STATEMENT: >>>
An Author adds a refines edge from one requirement version to another. ReqAML stores from/to version
UIDs and kind=refines, rejects self-edges, and audits the link. Edges never imply tree parenthood.
<<<
COMMENT: >>>
KIND: requirement
BASE_UID: E01
VERSION_N: 0
rbac_op: edge:create:refines
priority: 25
iteration: iter-r0
security.catalog_ref: AC-3
security.verification_note: AC-3 access enforcement; AU-2/3/12 where mutating.
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-EDGE
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: E02
STATUS: Active
TITLE: ConformsTo: Author request; Security/Steward apply (tree wins)
STATEMENT: >>>
ConformsTo authority is request/apply (permission tree wins). Author may create a conformance_pin_request (catalog:pin:request) only — Author does NOT apply pins (FIX-DENY-AUTHOR-PIN-APPLY / FIX-ALLOW-PIN-REQUEST). Security (standards imprint items) or Steward (non-standard) applies or denies via catalog:pin:apply|deny when bound to profile slot conforms_to_applicator (commercial may bind Author). Applied pin is (catalog_imprint_id, item_uid) — not a floating project UID pair. AO is approve-only on locked migrate (gate_signoff), never free pin edit.
<<<
COMMENT: >>>
KIND: requirement
BASE_UID: E02
VERSION_N: 0
rbac_op: edge:create:conforms_to
priority: 25
iteration: iter-r0
security.catalog_ref: AC-3
security.verification_note: AC-3 access enforcement; AU-2/3/12 where mutating.
edge: ← uses from FIX-DENY-AUTHOR-PIN-APPLY
edge: ← uses from FIX-ALLOW-PIN-REQUEST
edge: ← uses from FIX-ALLOW-SECURITY-PIN-APPLY
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-EDGE
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: E03
STATUS: Active
TITLE: Add edge uses
STATEMENT: >>>
An Author adds a uses edge when one architecture or capability version depends on another.
ReqAML records the dependency for impact analysis without cascading version forks.
<<<
COMMENT: >>>
KIND: requirement
BASE_UID: E03
VERSION_N: 0
rbac_op: edge:create:uses
priority: 30
iteration: iter-r1
security.catalog_ref: AC-3
security.verification_note: AC-3 access enforcement; AU-2/3/12 where mutating.
edge: ← refines from ARCH-HIER-USES-DEP
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-EDGE
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: E04
STATUS: Active
TITLE: Add edge satisfies
STATEMENT: >>>
An Author links a capability version to a requirement version via satisfies. At capability creation, Satisfies MUST be supplied (no orphan caps — ARCH-CAP-LINK). Additional Satisfies edges may be added later. ReqAML treats Satisfies as the primary coverage edge; the Satisfies edge itself is NOT a separate approve subject by default — CapabilityLine ApprovalRecord is enough for accepted solution (ARCH-CAP-APPROVE). Profiles may later add an EdgeSatisfies approve gate if configured.
<<<
COMMENT: >>>
KIND: requirement
BASE_UID: E04
VERSION_N: 0
rbac_op: edge:create:satisfies
priority: 20
iteration: iter-r0
security.catalog_ref: AC-3
security.verification_note: AC-3 access enforcement; AU-2/3/12 where mutating.
edge: ← refines from I02
edge: ← refines from ARCH-SEC-EDGE-DEDUPE-DB
edge: ← refines from ARCH-SEC-EDGE-DEDUPE-API
in_scope_of_contract: Design-2026-10
in_scope_of_contract: ReqALM product (build)
delivered_by_release: R1-core-ALM
edge: → uses to I02 (RELATIONS TYPE: Child; Parent would cycle)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-EDGE
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: I02
  ROLE: Uses
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: E05
STATUS: Active
TITLE: Remove edge
STATEMENT: >>>
An Author removes an edge. ReqAML deletes or tombstones the edge row and audits actor, kind, and
endpoints. Removal does not cascade-delete requirement versions.
<<<
COMMENT: >>>
KIND: requirement
BASE_UID: E05
VERSION_N: 0
rbac_op: edge:remove
priority: 40
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-EDGE
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: E06
STATUS: Active
TITLE: View traceability graph / matrix
STATEMENT: >>>
A Reader opens a traceability graph or matrix for selected versions. ReqAML returns edges filtered by
Scoped View and RBAC; export of matrix snapshots is optional later.
<<<
COMMENT: >>>
KIND: requirement
BASE_UID: E06
VERSION_N: 0
rbac_op: edge:matrix:read
priority: 35
iteration: iter-r1
security.catalog_ref: AC-3
security.verification_note: AC-3 access enforcement; AU-2/3/12 where mutating.
edge: ← satisfies from CAP-RELATIONS-API
edge: ← refines from ARCH-TRACE-VIEW-RTM
edge: ← refines from ARCH-TRACE-VIEW-CCM
edge: ← refines from ARCH-TRACE-LAYOUT-WORKER
edge: ← refines from ARCH-SEC-REL-STUB
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-EDGE
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: E07
STATUS: Active
TITLE: Navigate to linked control / capability
STATEMENT: >>>
From a requirement detail view, a Reader navigates to linked controls and capabilities via edges.
ReqAML resolves satisfies/conforms_to/uses/refines neighbors and opens the target version detail.
<<<
COMMENT: >>>
KIND: requirement
BASE_UID: E07
VERSION_N: 0
rbac_op: edge:navigate
priority: 35
iteration: iter-r0
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-EDGE
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: CAP-RELATIONS-API
STATUS: Active
TITLE: Read requirement relations (trace links API)
STATEMENT: >>>
Grant-scoped read-only relations API: GET /api/v1/projects/:projectId/requirements/:id/relations returns incoming and outgoing trace links grouped by kind (conforms_to, uses, satisfies, refines). Each link resolves the peer end with id, title, kind, and type for in-project lines and readable catalog controls in one response; cross-project and unreadable catalog peers return a non-revealing restricted stub. Dogfood seed loader persists trace_edges plus catalog imprint labels for ConformsTo pins.
<<<
COMMENT: >>>
KIND: capability
BASE_UID: CAP-RELATIONS-API
VERSION_N: 0
priority: 10
iteration: iter-r1
security.catalog_ref: AC-3
security.verification_note: Shipped with requirement relations read API PR #31 (merge cb8a8c97895b651c8f25ce660482e7e5e7ae4454).
edge: ← satisfies from CAP-BROWSE-UI-RELATIONS
edge: ← satisfies from CAP-BROWSE-UI-RELATIONS.1
in_scope_of_contract: ReqALM product (build)
delivered_by_release: R1 — requirement relations read API
<<<
RELATIONS:
- TYPE: Parent
  VALUE: SEC-EDGE
- TYPE: Parent
  VALUE: C08
  ROLE: Satisfies
- TYPE: Parent
  VALUE: E06
  ROLE: Satisfies
- TYPE: Parent
  VALUE: ARCH-API-RBAC
  ROLE: Satisfies
- TYPE: Parent
  VALUE: CAP-READ-REQS
  ROLE: Satisfies
- TYPE: Parent
  VALUE: CAP-SVC-OPERATION-ROUTE
  ROLE: Satisfies
- TYPE: Parent
  VALUE: ARCH-SEC-REL-STUB
  ROLE: Satisfies
- TYPE: Child
  VALUE: CONTRACT-ctr-reqalm-product
  ROLE: InScopeOf
- TYPE: Child
  VALUE: RELEASE-rel-r1-relations-api
  ROLE: Delivers

[REQUIREMENT]
UID: ARCH-TRACE-RECHECK
STATUS: Active
TITLE: Needs re-check (look-back completeness)
STATEMENT: >>>
Re-check (needs re-check) is a distinct state from incomplete: re-check applies to a criterion, control, or trace target that was previously complete whose conforming capability changed content, lost verification, or regressed. Incomplete means the target was never completed. Re-check shall be represented as trace_suspect (and review queues) separately from incomplete. Audit-sensitive targets — controls in the AU and AC families plus any target the user marks audit-sensitive — shall enter re-check when an upstream satisfying or conforming capability changes. A uses dependency change shall flag dependents for re-check without inheriting controls unless explicitly modeled.
<<<
COMMENT: >>>
KIND: requirement
BASE_UID: ARCH-TRACE-RECHECK
VERSION_N: 0
rbac_op: trace:suspect
priority: 15
iteration: iter-r1
security.catalog_ref: CM-3
security.verification_note: Groomed 2026-10-09; pre-write or UI track.
edge: ← uses from ARCH-HIER-USES-DEP
edge: ← uses from ARCH-SUSPECT.1
edge: ← refines from ARCH-TRACE-INHERIT-USES
edge: ← uses from ARCH-ATTACH-PIN-VERSION
edge: ← uses from ARCH-FIGMA
edge: ← uses from ARCH-ATTACH-PIN-VERSION.1
in_scope_of_contract: ReqALM product (build)
<<<
RELATIONS:
- TYPE: Parent
  VALUE: SEC-EDGE
- TYPE: Parent
  VALUE: ARCH-SUSPECT.1
  ROLE: Refines
- TYPE: Child
  VALUE: CONTRACT-ctr-reqalm-product
  ROLE: InScopeOf

[REQUIREMENT]
UID: ARCH-HIER-USES-DEP
STATUS: Active
TITLE: Uses dependency without control pass-through
STATEMENT: >>>
A uses edge shall model dependency, not ownership: for example a page capability uses a shared header capability. Uses shall not pass conforms_to controls along the edge unless explicitly annotated. When a used capability changes, dependents shall enter re-check per ARCH-TRACE-RECHECK.
<<<
COMMENT: >>>
KIND: requirement
BASE_UID: ARCH-HIER-USES-DEP
VERSION_N: 0
priority: 15
iteration: iter-r1
security.catalog_ref: CM-2
security.verification_note: Groomed 2026-10-09; pre-write or UI track. rbac_op trace:edit proposed for future trace mutation routes.
edge: ← refines from ARCH-TRACE-INHERIT-USES
in_scope_of_contract: ReqALM product (build)
<<<
RELATIONS:
- TYPE: Parent
  VALUE: SEC-EDGE
- TYPE: Parent
  VALUE: ARCH-TRACE-RECHECK
  ROLE: Uses
- TYPE: Parent
  VALUE: E03
  ROLE: Refines
- TYPE: Child
  VALUE: CONTRACT-ctr-reqalm-product
  ROLE: InScopeOf

[REQUIREMENT]
UID: ARCH-SEC-EDGE-DEDUPE-DB
STATUS: Active
TITLE: Trace edge dedupe index (DB)
STATEMENT: >>>
Before the first trace edge write route ships, trace_edges shall enforce a unique index on (from_project_id, from_uid, COALESCE(to_project_id,''), to_uid, kind, catalog_imprint_id) so cross-project peer project ids participate in deduplication at persistence.
<<<
COMMENT: >>>
KIND: requirement
BASE_UID: ARCH-SEC-EDGE-DEDUPE-DB
VERSION_N: 0
priority: 15
iteration: iter-r1
security.catalog_ref: CM-6
security.verification_note: Groomed 2026-10-09; pre-write or UI track.
in_scope_of_contract: ReqALM product (build)
<<<
RELATIONS:
- TYPE: Parent
  VALUE: SEC-EDGE
- TYPE: Parent
  VALUE: E04
  ROLE: Refines
- TYPE: Child
  VALUE: CONTRACT-ctr-reqalm-product
  ROLE: InScopeOf

[REQUIREMENT]
UID: ARCH-SEC-EDGE-DEDUPE-API
STATUS: Active
TITLE: Trace edge dedupe key (API)
STATEMENT: >>>
Trace edge create/update APIs shall treat the dedupe key as (from_project_id, from_uid, to_project_id, to_uid, kind, catalog_imprint_id) including the peer project id, matching the database uniqueness rule in ARCH-SEC-EDGE-DEDUPE-DB. The grant-scoped GET relations read API shall use the same peer-inclusive key when deduplicating edges in responses; requirements-relations.ts on main cb8a8c9 still omits the peer project id in its dedupe key — this requirement remains unsatisfied until a follow-up PR.
<<<
COMMENT: >>>
KIND: requirement
BASE_UID: ARCH-SEC-EDGE-DEDUPE-API
VERSION_N: 0
priority: 15
iteration: iter-r1
security.catalog_ref: AC-4
security.verification_note: Groomed 2026-10-09; pre-write or UI track.
in_scope_of_contract: ReqALM product (build)
<<<
RELATIONS:
- TYPE: Parent
  VALUE: SEC-EDGE
- TYPE: Parent
  VALUE: E04
  ROLE: Refines
- TYPE: Child
  VALUE: CONTRACT-ctr-reqalm-product
  ROLE: InScopeOf

[REQUIREMENT]
UID: ARCH-SEC-XPROJ-READ
STATUS: Active
TITLE: Cross-project link requires target read
STATEMENT: >>>
Creating a cross-project trace link shall require requirement:read on the target project. Conflict and dedupe errors shall not reveal edges the caller cannot read.
<<<
COMMENT: >>>
KIND: requirement
BASE_UID: ARCH-SEC-XPROJ-READ
VERSION_N: 0
rbac_op: requirement:tree:read
priority: 15
iteration: iter-r1
security.catalog_ref: AC-3
security.verification_note: Groomed 2026-10-09; pre-write or UI track.
edge: ← uses from ARCH-ATTACH-SCOPE
edge: ← uses from ARCH-ATTACH-SCOPE.1
in_scope_of_contract: ReqALM product (build)
<<<
RELATIONS:
- TYPE: Parent
  VALUE: SEC-EDGE
- TYPE: Parent
  VALUE: ARCH-API-RBAC.1
  ROLE: Refines
- TYPE: Child
  VALUE: CONTRACT-ctr-reqalm-product
  ROLE: InScopeOf

[REQUIREMENT]
UID: ARCH-SEC-REL-STUB
STATUS: Active
TITLE: Restricted relation stub shape
STATEMENT: >>>
Deliberate design choice: restricted relation stubs from unreadable projects shall reveal the count and kind of links (incoming/outgoing and relation_kind) without revealing peer ids, titles, or project identifiers.
<<<
COMMENT: >>>
KIND: requirement
BASE_UID: ARCH-SEC-REL-STUB
VERSION_N: 0
priority: 15
iteration: iter-r1
security.catalog_ref: AC-4
security.verification_note: Groomed 2026-10-09; pre-write or UI track.
edge: ← satisfies from CAP-RELATIONS-API
edge: ← uses from ARCH-ATTACH-SCOPE
edge: ← uses from ARCH-FIGMA-EGRESS
edge: ← uses from ARCH-ATTACH-SCOPE.1
in_scope_of_contract: ReqALM product (build)
<<<
RELATIONS:
- TYPE: Parent
  VALUE: SEC-EDGE
- TYPE: Parent
  VALUE: E06
  ROLE: Refines
- TYPE: Child
  VALUE: CONTRACT-ctr-reqalm-product
  ROLE: InScopeOf

[REQUIREMENT]
UID: ARCH-SEC-REL-PAGING
STATUS: Active
TITLE: Relations response paging
STATEMENT: >>>
Relations read responses shall support paging before large real datasets land (page size caps consistent with other browse APIs).
<<<
COMMENT: >>>
KIND: requirement
BASE_UID: ARCH-SEC-REL-PAGING
VERSION_N: 0
rbac_op: requirement:tree:read
priority: 15
iteration: iter-r1
security.catalog_ref: AC-3
security.verification_note: Groomed 2026-10-09; pre-write or UI track.
in_scope_of_contract: ReqALM product (build)
<<<
RELATIONS:
- TYPE: Parent
  VALUE: SEC-EDGE
- TYPE: Parent
  VALUE: ARCH-API
  ROLE: Refines
- TYPE: Child
  VALUE: CONTRACT-ctr-reqalm-product
  ROLE: InScopeOf

[REQUIREMENT]
UID: ARCH-TRACE-INHERIT-USES
STATUS: Draft
TITLE: Inherited controls over uses edges (common-control model)
STATEMENT: >>>
A provider capability version may mark any of its conforms_to pins inheritable (common control, NIST SP 800-53 Rev. 5 PL-2/PM-10 common-control designation). A consumer capability version that uses the provider inherits each inheritable pin and shows it as "inherited via uses <provider>". Rules: (1) Only capability-to-capability uses edges carry inheritance; uses edges from or to requirement lines remain dependency-only per ARCH-HIER-USES-DEP. (2) Only pins on the provider line's current active version that is shipped or verification_outcome=pass are inheritable; draft, superseded, obsolete or withdrawn provider versions supply nothing. (3) A control whose provider verification is fail, pending, or not assessed is not inherited; the consumer shows it "provider not-pass" and the control stays incomplete for the consumer. (4) Inheritance is one hop. A provider re-exports a control it inherited only when its own conforms_to pin for that control is marked inheritable (that is, it takes ownership of the control). (5) Any content, status, or verification change on the provider line, or a change to its inheritable set, flags needs re-check (trace_suspect) on every consumer for the affected controls only, per ARCH-TRACE-RECHECK. (6) Cross-project or restricted providers follow existing scope rules: a consumer without read grant on the provider project sees the inherited control id and the state "inherited (provider restricted)", but not the provider uid, statement, or evidence.
<<<
COMMENT: >>>
KIND: requirement
BASE_UID: ARCH-TRACE-INHERIT-USES
VERSION_N: 0
rbac_op: trace:edit
priority: 15
iteration: iter-r1
security.catalog_ref: PL-2
security.verification_note: Cyber 2026-10-09 inherit-uses mapping; common-control model per SP 800-53 Rev5 PL-2, PM-10, CA-2, SA-9.
edge: ← refines from ARCH-TRACE-INHERIT-HYBRID
in_scope_of_contract: ReqALM product (build)
edge: → conforms_to to PL-2 (pin imprint=nist-800-53@rev5-dogfood-20261006)
edge: → conforms_to to PM-10 (pin imprint=nist-800-53@rev5-dogfood-20261006)
edge: → conforms_to to CA-7 (pin imprint=nist-800-53@rev5-dogfood-20261006)
edge: → conforms_to to SA-17 (pin imprint=nist-800-53@rev5-dogfood-20261006)
<<<
RELATIONS:
- TYPE: Parent
  VALUE: SEC-EDGE
- TYPE: Parent
  VALUE: PL-2
  ROLE: ConformsTo
- TYPE: Parent
  VALUE: PM-10
  ROLE: ConformsTo
- TYPE: Parent
  VALUE: CA-7
  ROLE: ConformsTo
- TYPE: Parent
  VALUE: SA-17
  ROLE: ConformsTo
- TYPE: Parent
  VALUE: ARCH-TRACE-RECHECK
  ROLE: Refines
- TYPE: Parent
  VALUE: ARCH-HIER-USES-DEP
  ROLE: Refines
- TYPE: Child
  VALUE: CONTRACT-ctr-reqalm-product
  ROLE: InScopeOf

[REQUIREMENT]
UID: ARCH-TRACE-INHERIT-HYBRID
STATUS: Draft
TITLE: Hybrid controls (provider-supplied plus consumer direct link)
STATEMENT: >>>
When a consumer capability both inherits a control via uses and has its own direct conforms_to pin for the same control, the control is hybrid for that consumer: the provider supplies the shared part and the consumer adds or overrides the rest (for example a custom session timeout). The consumer's direct pin wins for display and for the consumer's verification state, labeled "hybrid (via <provider>)". Hybrid counts once per consumer and control. A provider change still flags the hybrid control for re-check on the consumer. Removing the direct pin returns the control to inherited; removing the provider inheritable mark returns it to direct-only.
<<<
COMMENT: >>>
KIND: requirement
BASE_UID: ARCH-TRACE-INHERIT-HYBRID
VERSION_N: 0
rbac_op: trace:edit
priority: 15
iteration: iter-r1
security.catalog_ref: CA-2
security.verification_note: Cyber 2026-10-09; hybrid control per SP 800-53 Rev5 PL-2 discussion (common, hybrid, system-specific).
in_scope_of_contract: ReqALM product (build)
edge: → conforms_to to PL-2 (pin imprint=nist-800-53@rev5-dogfood-20261006)
edge: → conforms_to to CA-2 (pin imprint=nist-800-53@rev5-dogfood-20261006)
<<<
RELATIONS:
- TYPE: Parent
  VALUE: SEC-EDGE
- TYPE: Parent
  VALUE: PL-2
  ROLE: ConformsTo
- TYPE: Parent
  VALUE: CA-2
  ROLE: ConformsTo
- TYPE: Parent
  VALUE: ARCH-TRACE-INHERIT-USES
  ROLE: Refines
- TYPE: Child
  VALUE: CONTRACT-ctr-reqalm-product
  ROLE: InScopeOf

[REQUIREMENT]
UID: CAP-TRACE-INHERIT-USES
STATUS: Active
TITLE: Trace inheritable ConformsTo loader + seed beds
STATEMENT: >>>
Dogfood seed loader persists trace_edges.inheritable on capability conforms_to pins; validation rejects inheritable on non-capability sources or non-conforms_to edges. Read APIs resolve inherited and hybrid control state at read time in a follow-on PR.
<<<
COMMENT: >>>
KIND: capability
BASE_UID: CAP-TRACE-INHERIT-USES
VERSION_N: 0
priority: 10
iteration: iter-r1
security.catalog_ref: CM-2
security.verification_note: Shipped with inherit-uses loader PR #39 (merge 56bfc4d6a9fe04559ccddae636ec4052d84ae907).
in_scope_of_contract: ReqALM product (build)
delivered_by_release: R1 — trace inheritable controls over uses
<<<
RELATIONS:
- TYPE: Parent
  VALUE: SEC-EDGE
- TYPE: Child
  VALUE: CONTRACT-ctr-reqalm-product
  ROLE: InScopeOf
- TYPE: Child
  VALUE: RELEASE-rel-r1-trace-inherit-uses
  ROLE: Delivers

[[/SECTION]]

[[SECTION]]
UID: SEC-CT
TITLE: Contracts

[TEXT]
UID: SEC-CT-INTRO
STATEMENT: >>>
Contracts are junction overlays that mark requirement versions in_scope_of a named agreement. Document views filter by contract and optionally walk parent lines.
<<<

[REQUIREMENT]
UID: ARCH-CONTRACT
STATUS: Deleted
TITLE: Contracts as overlays
STATEMENT: >>>
Contracts mark requirements in scope of an agreement. (Initial wording — superseded.)
<<<
COMMENT: >>>
KIND: requirement
BASE_UID: ARCH-CONTRACT
VERSION_N: 0
priority: 15
iteration: iter-r0
security.catalog_ref: AC-3
security.verification_note: AC-3 access enforcement; AU-2/3/12 where mutating.
edge: ← uses from ARCH-CAT-FREEZE
in_scope_of_contract: Legacy intake (closed)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CT
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-legacy-intake-closed
  ROLE: InScopeOf
- TYPE: Child
  VALUE: RELEASE-rel-r1-core-alm
  ROLE: Delivers

[REQUIREMENT]
UID: ARCH-CONTRACT.1
STATUS: Active
TITLE: Contracts as overlays
STATEMENT: >>>
Contracts are related overlays, not tree parents. A contract links requirement version UIDs via
in_scope_of; document views filter by contract and optionally walk parent lines for context.
Overlapping contracts may share version UIDs; closing a contract does not delete requirement versions.
<<<
COMMENT: >>>
KIND: requirement
BASE_UID: ARCH-CONTRACT
VERSION_N: 1
priority: 15
iteration: iter-r0
security.catalog_ref: AC-3
security.verification_note: AC-3 access enforcement; AU-2/3/12 where mutating.
edge: ← uses from F07
edge: ← uses from L02
edge: ← uses from F04
edge: ← satisfies from CAP-REQALM-CONTRACTS
edge: ← satisfies from CAP-CONTRACTS-LOADER
edge: ← satisfies from CAP-READ-CONTRACTS
in_scope_of_contract: Design-2026-10
in_scope_of_contract: ReqALM product (build)
delivered_by_release: R1-core-ALM
edge: → uses to ARCH-CONTRACT-DOC (RELATIONS TYPE: Child; Parent would cycle)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CT
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: ARCH-CONTRACT-DOC
  ROLE: Uses
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[[SECTION]]
UID: ARCH-CONTRACT-CHILDREN
TITLE: Children of ARCH-CONTRACT

[REQUIREMENT]
UID: ARCH-CONTRACT-DOC
STATUS: Active
TITLE: Document view walk from contract
STATEMENT: >>>
Opening a document view from a contract filters to in_scope_of version UIDs and may walk parent lines
to include section context. Toggle include-context-parents controls whether ancestors outside the junction
set are shown for readability (see mockup 03).
<<<
COMMENT: >>>
KIND: requirement
BASE_UID: ARCH-CONTRACT-DOC
VERSION_N: 0
priority: 20
iteration: iter-r0
security.catalog_ref: AC-3
security.verification_note: AC-3 access enforcement; AU-2/3/12 where mutating.
edge: ← uses from ARCH-CONTRACT.1
edge: ← refines from F07
edge: ← refines from FIX-CONTRACT-DOC-NOCTX
edge: ← refines from FIX-CONTRACT-DOC-CTX
in_scope_of_contract: Design-2026-10
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: ARCH-CONTRACT.1
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf

[[/SECTION]]

[REQUIREMENT]
UID: F01
STATUS: Active
TITLE: Create contract
STATEMENT: >>>
A Project admin or Author creates a contract with name, dates, and status. ReqAML inserts a contract
row as a junction overlay (not a tree parent) and audits the create.
<<<
COMMENT: >>>
KIND: requirement
BASE_UID: F01
VERSION_N: 0
rbac_op: contract:create
priority: 20
iteration: iter-r0
security.catalog_ref: AC-3
security.verification_note: AC-3 access enforcement; AU-2/3/12 where mutating.
edge: ← satisfies from CAP-CONTRACT-UI
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CT
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: F02
STATUS: Active
TITLE: Update contract metadata
STATEMENT: >>>
An Author updates contract dates, name, or status (while not closed). ReqAML persists metadata changes
without altering in_scope_of membership unless a separate link/unlink is issued.
<<<
COMMENT: >>>
KIND: requirement
BASE_UID: F02
VERSION_N: 0
rbac_op: contract:update
priority: 35
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CT
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: F03
STATUS: Active
TITLE: Close contract
STATEMENT: >>>
A Project admin closes a contract. ReqAML sets status closed and freezes membership edits
(link/unlink/bulk_link deny — FIX-DENY-CLOSED-LINK); requirement versions remain in the store.
Document view stays readable. Reopening requires an explicit admin action (later policy).
<<<
COMMENT: >>>
KIND: requirement
BASE_UID: F03
VERSION_N: 0
rbac_op: contract:close
priority: 50
iteration: iter-r2
security.catalog_ref: AC-3
security.verification_note: AC-3 access enforcement; AU-2/3/12 where mutating.
edge: ← uses from FIX-DENY-CLOSED-LINK
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CT
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: F04
STATUS: Active
TITLE: Link requirement version to contract
STATEMENT: >>>
An Author links a requirement version UID into a contract's in_scope_of set. ReqAML validates the
version exists in the scoped project and rejects links when the contract is closed (FIX-DENY-CLOSED-LINK).
The junction change is audited.
<<<
COMMENT: >>>
KIND: requirement
BASE_UID: F04
VERSION_N: 0
rbac_op: contract:link
priority: 20
iteration: iter-r0
security.catalog_ref: AC-3
security.verification_note: AC-3 access enforcement; AU-2/3/12 where mutating.
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CT
- TYPE: Parent
  VALUE: ARCH-CONTRACT.1
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: F05
STATUS: Active
TITLE: Unlink requirement version from contract
STATEMENT: >>>
An Author unlinks a version UID from a contract. ReqAML removes the junction membership and audits
the change. Closed contracts reject unlink as well as link; versions themselves are untouched.
<<<
COMMENT: >>>
KIND: requirement
BASE_UID: F05
VERSION_N: 0
rbac_op: contract:unlink
priority: 35
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CT
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: F06
STATUS: Active
TITLE: Bulk-link versions to contract
STATEMENT: >>>
An Author bulk-links a set of version UIDs to a contract in one transaction. ReqAML applies all-or-nothing
membership updates and audits the batch size and actor.
<<<
COMMENT: >>>
KIND: requirement
BASE_UID: F06
VERSION_N: 0
rbac_op: contract:bulk_link
priority: 40
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CT
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: F07
STATUS: Active
TITLE: Open document view from contract
STATEMENT: >>>
A Reader opens a document view built from a contract. ReqAML filters to in_scope_of versions, optionally
walks parent lines for section context, and renders a readable document (mockup 03).
<<<
COMMENT: >>>
KIND: requirement
BASE_UID: F07
VERSION_N: 0
rbac_op: contract:document_view
priority: 15
iteration: iter-r0
security.catalog_ref: AC-3
security.verification_note: AC-3 access enforcement; AU-2/3/12 where mutating.
edge: ← satisfies from CAP-CONTRACT-UI
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CT
- TYPE: Parent
  VALUE: ARCH-CONTRACT-DOC
  ROLE: Refines
- TYPE: Parent
  VALUE: ARCH-CONTRACT.1
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: F08
STATUS: Active
TITLE: Toggle include context parents
STATEMENT: >>>
A Reader toggles whether document view includes ancestor lines outside the contract junction set.
The toggle is a view preference; it does not mutate in_scope_of.
<<<
COMMENT: >>>
KIND: requirement
BASE_UID: F08
VERSION_N: 0
rbac_op: contract:document_view:context
priority: 45
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CT
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: F09
STATUS: Active
TITLE: View contract overlap timeline
STATEMENT: >>>
A Reader views overlapping contracts on a timeline by starts_on/ends_on. ReqAML returns contracts for
the scoped client/project so reviewers can see concurrent agreement scopes.
<<<
COMMENT: >>>
KIND: requirement
BASE_UID: F09
VERSION_N: 0
rbac_op: contract:timeline
priority: 50
iteration: iter-r2
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CT
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: F10
STATUS: Active
TITLE: List contracts for client/project
STATEMENT: >>>
A Reader lists contracts for the scoped client/project. ReqAML returns name, status, and date fields
permission-filtered to the caller's access. Closed contracts appear in lists but membership is frozen.
<<<
COMMENT: >>>
KIND: requirement
BASE_UID: F10
VERSION_N: 0
rbac_op: contract:list
priority: 25
iteration: iter-r0
security.catalog_ref: AC-3
security.verification_note: AC-3 access enforcement; AU-2/3/12 where mutating.
edge: ← satisfies from CAP-CONTRACT-UI
edge: ← satisfies from CAP-CONTRACTS-LOADER
edge: ← satisfies from CAP-READ-CONTRACTS
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CT
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: CAP-REQALM-CONTRACTS
STATUS: Active
TITLE: ReqALM product and maintenance contracts (seed)
STATEMENT: >>>
Seed-only contract overlay pass: ReqALM product contract (ctr-reqalm-product) covers all reqalm releases via covers_releases; in_scope_of pins active reqalm capability/requirement tips; maintenance contract (ctr-reqalm-maintenance) owns draft CAP-UPKEEP-* capabilities satisfying SYS-CYBER-UPKEEP. Regenerates docs/design/seed/out/, schema docs, and HANDOFF.md. No application runtime changes.
<<<
COMMENT: >>>
KIND: capability
BASE_UID: CAP-REQALM-CONTRACTS
VERSION_N: 0
priority: 10
iteration: iter-r1
security.catalog_ref: CM-2
security.verification_note: Shipped with ReqALM contracts seed PR #38 (merge 88df54dea5c8d2bfd895e2613b17dbf2c5b3405f).
in_scope_of_contract: ReqALM product (build)
delivered_by_release: R1 — ReqALM product and maintenance contracts (seed)
edge: → conforms_to to CM-2 (pin imprint=nist-800-53@rev5-dogfood-20261006)
<<<
RELATIONS:
- TYPE: Parent
  VALUE: SEC-CT
- TYPE: Parent
  VALUE: ARCH-CONTRACT.1
  ROLE: Satisfies
- TYPE: Parent
  VALUE: ARCH-RELEASE
  ROLE: Satisfies
- TYPE: Parent
  VALUE: MC03
  ROLE: Satisfies
- TYPE: Parent
  VALUE: CM-2
  ROLE: ConformsTo
- TYPE: Child
  VALUE: CONTRACT-ctr-reqalm-product
  ROLE: InScopeOf
- TYPE: Child
  VALUE: RELEASE-rel-r1-reqalm-contracts
  ROLE: Delivers

[REQUIREMENT]
UID: CAP-SEED-ATTACH-FIGMA
STATUS: Active
TITLE: Cyber attachments + Figma requirements (seed)
STATEMENT: >>>
Seed-only: Cyber attachments and Figma design-link requirement set in dogfood.yaml (ARCH-ATTACH-*, ARCH-ATTACH-VERSIONS, ARCH-ATTACH-SCAN, ARCH-FIGMA-*, SPIKE-FIGMA-FEASIBILITY, CAP-ATTACH-*, ARCH-KEY-SCOPE.1 and attachment .1 content mints) with conforms_to, refines, uses, and satisfies edges from fixtures/cyber-attach-figma-snippet.yaml and delta-versions.yaml. Regenerates out/ and HANDOFF.md. No application runtime changes; ships parallel PR #39 rel-r1-trace-inherit-uses only (this PR's release stays planned).
<<<
COMMENT: >>>
KIND: capability
BASE_UID: CAP-SEED-ATTACH-FIGMA
VERSION_N: 0
priority: 10
iteration: iter-r1
security.catalog_ref: CM-2
security.verification_note: Shipped with attachments/Figma seed PR #40 (merge 1eb8482b533b5f656240bc7b53a60b1a58c5a203).
in_scope_of_contract: ReqALM product (build)
delivered_by_release: R1 — Cyber attachments + Figma requirements (seed)
edge: → conforms_to to CM-2 (pin imprint=nist-800-53@rev5-dogfood-20261006)
<<<
RELATIONS:
- TYPE: Parent
  VALUE: SEC-CT
- TYPE: Parent
  VALUE: ARCH-ATTACH
  ROLE: Satisfies
- TYPE: Parent
  VALUE: ARCH-FIGMA
  ROLE: Satisfies
- TYPE: Parent
  VALUE: CM-2
  ROLE: ConformsTo
- TYPE: Child
  VALUE: CONTRACT-ctr-reqalm-product
  ROLE: InScopeOf
- TYPE: Child
  VALUE: RELEASE-rel-r1-seed-attach-figma
  ROLE: Delivers

[[/SECTION]]

[[SECTION]]
UID: SEC-REL
TITLE: Releases

[TEXT]
UID: SEC-REL-INTRO
STATEMENT: >>>
Releases snapshot the requirement versions they deliver; they are not tree parents. Planned backlog, ship freeze, and release diff live here.
<<<

[REQUIREMENT]
UID: ARCH-RELEASE
STATUS: Active
TITLE: Releases deliver version snapshots
STATEMENT: >>>
A release delivers a snapshot of requirement version UIDs. Shipping freezes the delivered set; releases
do not own the requirement tree. Planned releases may be edited until ship.
<<<
COMMENT: >>>
KIND: requirement
BASE_UID: ARCH-RELEASE
VERSION_N: 0
priority: 15
iteration: iter-r0
security.catalog_ref: AC-3
security.verification_note: AC-3 access enforcement; AU-2/3/12 where mutating.
edge: ← uses from L04
edge: ← uses from G03
edge: ← satisfies from CAP-REQALM-CONTRACTS
edge: ← satisfies from CAP-UI-VIEW-CAP-FOCUS
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-REL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[[SECTION]]
UID: ARCH-RELEASE-CHILDREN
TITLE: Children of ARCH-RELEASE

[REQUIREMENT]
UID: ARCH-RELEASE-FREEZE
STATUS: Active
TITLE: Ship freezes delivered set
STATEMENT: >>>
On ship, ReqAML freezes the delivers list as an immutable snapshot. Further edits require a new planned
release or an explicit reopen policy (out of scope for R0). Diff against prior shipped releases uses UID sets.
Attempts to mutate shipped delivers deny under CM-3 (FIX-DENY-SHIPPED-DELIVERS).
<<<
COMMENT: >>>
KIND: requirement
BASE_UID: ARCH-RELEASE-FREEZE
VERSION_N: 0
priority: 20
iteration: iter-r1
security.catalog_ref: CM-3
security.verification_note: CM-3 configuration change control on shipped delivers. ASD STIG V6R4 V-222407 context.
edge: ← refines from G05
edge: ← refines from FIX-REL-SNAP
edge: ← uses from ARCH-CAT-FREEZE
in_scope_of_contract: Design-2026-10
in_scope_of_contract: ReqALM product (build)
edge: → conforms_to to CM-3 (pin imprint=nist-800-53@rev5-dogfood-20261006)
edge: → conforms_to to V-222407 (pin imprint=asd-stig@v6r4)
<<<
RELATIONS:
- TYPE: Parent
  VALUE: ARCH-RELEASE
- TYPE: Parent
  VALUE: CM-3
  ROLE: ConformsTo
- TYPE: Parent
  VALUE: V-222407
  ROLE: ConformsTo
- TYPE: Child
  VALUE: CONTRACT-contract-design-2026-10
  ROLE: InScopeOf
- TYPE: Child
  VALUE: CONTRACT-ctr-reqalm-product
  ROLE: InScopeOf

[[/SECTION]]

[REQUIREMENT]
UID: G01
STATUS: Active
TITLE: Create planned release
STATEMENT: >>>
A Release manager creates a planned release with name and planned_on date. ReqAML inserts a release
row with empty delivers and status planned. Creation is audited; shipped snapshots cannot be created
directly — ship is a separate action (G05).
<<<
COMMENT: >>>
KIND: requirement
BASE_UID: G01
VERSION_N: 0
rbac_op: release:create
priority: 20
iteration: iter-r0
security.catalog_ref: AC-3
security.verification_note: AC-3 access enforcement; AU-2/3/12 where mutating.
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-REL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: G02
STATUS: Active
TITLE: Update planned release
STATEMENT: >>>
A Release manager updates a planned release's name or planned_on. Shipped releases reject metadata
edits. Updates are audited; this does not alter the delivers UID set (see G03).
<<<
COMMENT: >>>
KIND: requirement
BASE_UID: G02
VERSION_N: 0
rbac_op: release:update
priority: 35
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-REL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: G03
STATUS: Active
TITLE: Add/remove versions on planned release
STATEMENT: >>>
A Release manager adds or removes requirement version UIDs on a planned release's delivers set.
ReqAML validates UIDs and rejects mutations on shipped releases (FIX-DENY-SHIPPED-DELIVERS). Membership
changes on planned releases are audited; freeze pairs ARCH-RELEASE-FREEZE / CM-3.
<<<
COMMENT: >>>
KIND: requirement
BASE_UID: G03
VERSION_N: 0
rbac_op: release:membership
priority: 20
iteration: iter-r0
security.catalog_ref: AC-3
security.verification_note: AC-3 access enforcement; AU-2/3/12 where mutating.
edge: ← uses from FIX-DENY-SHIPPED-DELIVERS
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-REL
- TYPE: Parent
  VALUE: ARCH-RELEASE
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: G04
STATUS: Active
TITLE: Prioritize release backlog from priorities
STATEMENT: >>>
A Release manager orders the planned release backlog using requirement version priorities. ReqAML
exposes a sorted candidate list; membership changes remain explicit add/remove operations.
<<<
COMMENT: >>>
KIND: requirement
BASE_UID: G04
VERSION_N: 0
rbac_op: release:prioritize
priority: 40
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-REL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: G05
STATUS: Active
TITLE: Ship release (freeze snapshot)
STATEMENT: >>>
A Release manager ships a release. ReqAML sets status shipped, records shipped_on, and freezes delivers as an immutable snapshot. Ship is a high-value auditable event (AU-2/3/12). Further delivers mutations deny (FIX-DENY-SHIPPED-DELIVERS). ActionHook release:ship evaluates profile Gates: gate-cyber-ship when release.cyber_gate=true and enabled (ARCH-CYBER-GATE); gate-verification-ship when enabled (ARCH-VERIFICATION-GATE). Without those gates enabled/triggered, Release manager ships without AO / verification pass.
<<<
COMMENT: >>>
KIND: requirement
BASE_UID: G05
VERSION_N: 0
rbac_op: release:ship
priority: 15
iteration: iter-r1
security.catalog_ref: AU-2
security.verification_note: Ship is a high-value auditable event (AU-2/3/12).
edge: ← refines from ARCH-OTEL
edge: ← refines from ARCH-CRED-REAUTH
in_scope_of_contract: Design-2026-10
in_scope_of_contract: ReqALM product (build)
delivered_by_release: R1-core-ALM
edge: → conforms_to to AU-2 (pin imprint=nist-800-53@rev5-dogfood-20261006)
edge: → conforms_to to AU-12 (pin imprint=nist-800-53@rev5-dogfood-20261006)
edge: → conforms_to to AU-3 (pin imprint=nist-800-53@rev5-dogfood-20261006)
<<<
RELATIONS:
- TYPE: Parent
  VALUE: SEC-REL
- TYPE: Parent
  VALUE: AU-2
  ROLE: ConformsTo
- TYPE: Parent
  VALUE: ARCH-RELEASE-FREEZE
  ROLE: Refines
- TYPE: Parent
  VALUE: AU-12
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: G06
STATUS: Active
TITLE: View snapshot vs prior release
STATEMENT: >>>
A Reader diffs a release snapshot against a prior release. ReqAML computes added/removed/unchanged
version UIDs from frozen delivers sets. Diff is read-only and scoped to the project.
<<<
COMMENT: >>>
KIND: requirement
BASE_UID: G06
VERSION_N: 0
rbac_op: release:diff
priority: 35
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-REL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: G07
STATUS: Active
TITLE: Gantt / schedule view from releases + priorities + iterations
STATEMENT: >>>
A Reader opens a Gantt / schedule view derived from releases, priorities, and iterations (ARCH-GANTT). ReqAML provides a first-class schedule read model for planning — alongside backlog planning views (ARCH-BACKLOG / G04 / K01). Schedule overlays show release windows, iteration bands, and prioritized work; they are product requirements, not exploratory-only.
<<<
COMMENT: >>>
KIND: requirement
BASE_UID: G07
VERSION_N: 0
rbac_op: release:gantt
priority: 30
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-REL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: G08
STATUS: Active
TITLE: List releases for project
STATEMENT: >>>
A Reader lists releases for the scoped project. ReqAML returns planned and shipped releases with
dates and status, permission-filtered by project grants. Cross-client leakage is blocked by server-bound
Client Scoped View. List reads are low-sensitivity but still scoped.
<<<
COMMENT: >>>
KIND: requirement
BASE_UID: G08
VERSION_N: 0
rbac_op: release:list
priority: 25
iteration: iter-r0
security.catalog_ref: AC-3
security.verification_note: AC-3 access enforcement; AU-2/3/12 where mutating.
edge: ← satisfies from CAP-READ-RELEASES
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-REL
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: ARCH-CYBER-GATE
STATUS: Active
TITLE: gate-cyber-ship Gate instance (release.cyber_gate example)
STATEMENT: >>>
cyber_gate is modeled as Gate instance gate-cyber-ship under WorkflowProfile (ARCH-GATE-MODEL), not a one-off flag-only path. Optional boolean release.cyber_gate remains the per-release switch; when true AND the profile enables gate-cyber-ship, G05 ship requires Security cyber sign-off plus AO approve (RoleBinding slots security_signoff + ao_approve) before freeze. When false/absent or gate disabled, Release manager ships without AO. Ship-gate only — not a full ATO workflow. Other ship gates (e.g. gate-verification-ship) compose the same way.
<<<
COMMENT: >>>
KIND: requirement
BASE_UID: ARCH-CYBER-GATE
VERSION_N: 0
rbac_op: release:cyber_gate
priority: 20
iteration: iter-r1
security.catalog_ref: CM-3
security.verification_note: Cyber gate ship: Security sign-off + AO approve. Partial ATO — ship gate only.
edge: ← uses from ARCH-GATE-SIGNOFF
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-REL
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: ARCH-GANTT
STATUS: Active
TITLE: Gantt / schedule views as product requirements (with backlog)
STATEMENT: >>>
Gantt / schedule views are first-class product requirements (G07): schedule read model over releases, priorities, and iterations with overlays for release windows and iteration bands. Defined alongside backlog planning (ARCH-BACKLOG) — both are wanted; neither is marked defer or v1-only cut.
<<<
COMMENT: >>>
KIND: requirement
BASE_UID: ARCH-GANTT
VERSION_N: 0
rbac_op: release:gantt
priority: 25
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-REL
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[[/SECTION]]

[[SECTION]]
UID: SEC-CAT
TITLE: Catalogs

[TEXT]
UID: SEC-CAT-INTRO
STATEMENT: >>>
Catalogs provide standard and project templates. Standard catalogs (NIST/STIG) are versioned as imprints; project REQAML-SEC-* entries are steward-mutable until imprint publish. Stewardship, browse, reference, copy, imprint publish, import-diff, drift review, migrate-to-imprint (preview + apply), and pin semantics live here.
<<<

[REQUIREMENT]
UID: H01
STATUS: Active
TITLE: Create catalog
STATEMENT: >>>
A catalog steward creates a catalog at global, client, or project scope. ReqAML inserts catalog
metadata with is_standard flag; standard catalogs are immutable after publish policy.
<<<
COMMENT: >>>
KIND: requirement
BASE_UID: H01
VERSION_N: 0
rbac_op: catalog:create
priority: 40
iteration: iter-r1
security.catalog_ref: REQALM-SEC-CATALOG
security.verification_note: Catalog steward gates; standard catalogs read-only. AC-3/CM-5 aligned.
edge: ← refines from ARCH-CAT-SCOPE
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: SEC-CAT
- TYPE: Parent
  VALUE: AC-3
  ROLE: ConformsTo
- TYPE: Parent
  VALUE: CM-5
  ROLE: ConformsTo
- TYPE: Child
  VALUE: CONTRACT-ctr-reqalm-product
  ROLE: InScopeOf

[REQUIREMENT]
UID: H02
STATUS: Active
TITLE: Update catalog metadata
STATEMENT: >>>
A steward updates catalog title or scope metadata where mutable. Standard catalog titles may be
display-only; ReqAML rejects mutations that would rewrite published standard entry ids.
<<<
COMMENT: >>>
KIND: requirement
BASE_UID: H02
VERSION_N: 0
rbac_op: catalog:update
priority: 50
iteration: iter-r1
security.catalog_ref: REQALM-SEC-CATALOG
security.verification_note: Catalog steward gates; standard catalogs read-only. AC-3/CM-5 aligned.
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: SEC-CAT
- TYPE: Parent
  VALUE: AC-3
  ROLE: ConformsTo
- TYPE: Parent
  VALUE: CM-5
  ROLE: ConformsTo
- TYPE: Child
  VALUE: CONTRACT-ctr-reqalm-product
  ROLE: InScopeOf

[REQUIREMENT]
UID: H03
STATUS: Active
TITLE: Publish catalog imprint
STATEMENT: >>>
A Catalog steward publishes a catalog imprint (library revision + import identity), e.g. nist-800-53@rev5-dogfood-20261006 or asd-stig@v6r4. ReqAML freezes item rows for that imprint — published catalog item rows are never rewritten in place; a later import creates a new imprint. Standard catalogs (is_standard) always require imprint publish before ConformsTo pins may target them. Project catalogs (REQAML-SEC-*) may stay steward-mutable without an imprint until the steward publishes one. Publish is steward-only and audited (actor, catalog_id, imprint_id).
<<<
COMMENT: >>>
KIND: requirement
BASE_UID: H03
VERSION_N: 0
rbac_op: catalog:publish
priority: 55
iteration: iter-r2
security.catalog_ref: REQALM-SEC-CATALOG
security.verification_note: Catalog steward gates; standard catalogs imprint-published read-only. AC-3/CM-5 aligned. Pins are (imprint_id, item_uid).
edge: ← refines from ARCH-CAT-IMPRINT
edge: ← uses from ARCH-CAT-IMPORT
edge: ← refines from ARCH-CAT-SCOPE
edge: ← uses from ARCH-CAT-MIGRATE
edge: ← uses from H10
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: SEC-CAT
- TYPE: Parent
  VALUE: AC-3
  ROLE: ConformsTo
- TYPE: Parent
  VALUE: CM-5
  ROLE: ConformsTo
- TYPE: Child
  VALUE: CONTRACT-ctr-reqalm-product
  ROLE: InScopeOf

[[SECTION]]
UID: H03-CHILDREN
TITLE: Children of H03

[REQUIREMENT]
UID: ARCH-CAT-IMPRINT
STATUS: Active
TITLE: Catalog imprint model
STATEMENT: >>>
Standard catalogs are versioned as imprints: each imprint binds a library_revision and import_identity (e.g. nist-800-53@rev5-<import>, asd-stig@v6r4). Item UIDs (AC-3, V-222536) are stable within an imprint. Published imprint item rows are never rewritten in place; a new import yields a new imprint.
<<<
COMMENT: >>>
KIND: requirement
BASE_UID: ARCH-CAT-IMPRINT
VERSION_N: 0
rbac_op: catalog:imprint:model
priority: 20
iteration: iter-r0
security.catalog_ref: REQALM-SEC-CATALOG
security.verification_note: Catalog steward gates; standard catalogs imprint-published read-only. AC-3/CM-5 aligned. Pins are (imprint_id, item_uid).
edge: ← uses from ARCH-CAT-PIN
edge: ← uses from ARCH-CAT-IMPORT
edge: ← refines from ARCH-CAT-EXTERNAL
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: H03
- TYPE: Parent
  VALUE: H03
  ROLE: Refines
- TYPE: Parent
  VALUE: AC-3
  ROLE: ConformsTo
- TYPE: Parent
  VALUE: CM-5
  ROLE: ConformsTo
- TYPE: Child
  VALUE: CONTRACT-ctr-reqalm-product
  ROLE: InScopeOf

[[SECTION]]
UID: ARCH-CAT-IMPRINT-CHILDREN
TITLE: Children of ARCH-CAT-IMPRINT

[REQUIREMENT]
UID: ARCH-CAT-PIN
STATUS: Active
TITLE: ConformsTo pin is (imprint_id, item_uid)
STATEMENT: >>>
ConformsTo edges resolve through the imprint. Pin shape is (catalog_imprint_id, item_uid): YAML keeps to: as the stable item UID (AC-3, V-222536) and catalog_imprint_id naming the imprint. Resolution does not use a floating global UID alone.
<<<
COMMENT: >>>
KIND: requirement
BASE_UID: ARCH-CAT-PIN
VERSION_N: 0
rbac_op: catalog:imprint:pin
priority: 20
iteration: iter-r0
security.catalog_ref: REQALM-SEC-CATALOG
security.verification_note: Catalog steward gates; standard catalogs imprint-published read-only. AC-3/CM-5 aligned. Pins are (imprint_id, item_uid).
edge: ← uses from ARCH-CAT-REACT
edge: ← uses from ARCH-CAT-FREEZE
edge: ← uses from ARCH-CAT-MIGRATE
edge: ← refines from ARCH-SEC-CAT-LABEL-IMPRINT
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: ARCH-CAT-IMPRINT
- TYPE: Parent
  VALUE: H06
  ROLE: Refines
- TYPE: Parent
  VALUE: ARCH-CAT-IMPRINT
  ROLE: Uses
- TYPE: Parent
  VALUE: AC-3
  ROLE: ConformsTo
- TYPE: Parent
  VALUE: CM-5
  ROLE: ConformsTo
- TYPE: Child
  VALUE: CONTRACT-ctr-reqalm-product
  ROLE: InScopeOf

[[SECTION]]
UID: ARCH-CAT-PIN-CHILDREN
TITLE: Children of ARCH-CAT-PIN

[REQUIREMENT]
UID: ARCH-CAT-FREEZE
STATUS: Active
TITLE: Contracts/releases keep historical ConformsTo pins
STATEMENT: >>>
Contracts and releases are not changed automatically on catalog import. They already pin requirement version UIDs; those versions retain their historical ConformsTo pins (imprint_id, item_uid) for historical compliance.
<<<
COMMENT: >>>
KIND: requirement
BASE_UID: ARCH-CAT-FREEZE
VERSION_N: 0
rbac_op: catalog:imprint:freeze
priority: 25
iteration: iter-r0
security.catalog_ref: REQALM-SEC-CATALOG
security.verification_note: Catalog steward gates; standard catalogs imprint-published read-only. AC-3/CM-5 aligned. Pins are (imprint_id, item_uid).
edge: ← uses from ARCH-CAT-MIGRATE
in_scope_of_contract: ReqALM product (build)
edge: → conforms_to to AU-12 (pin imprint=nist-800-53@rev5-dogfood-20261006)
<<<
RELATIONS:
- TYPE: Parent
  VALUE: ARCH-CAT-PIN
- TYPE: Parent
  VALUE: ARCH-CAT-PIN
  ROLE: Uses
- TYPE: Parent
  VALUE: ARCH-RELEASE-FREEZE
  ROLE: Uses
- TYPE: Parent
  VALUE: ARCH-CONTRACT
  ROLE: Uses
- TYPE: Parent
  VALUE: AU-12
  ROLE: ConformsTo
- TYPE: Child
  VALUE: CONTRACT-ctr-reqalm-product
  ROLE: InScopeOf

[[/SECTION]]

[REQUIREMENT]
UID: ARCH-CAT-IMPORT
STATUS: Active
TITLE: Import imprint diffs; no auto-retarget
STATEMENT: >>>
When a steward imports a new imprint of a standard catalog, ReqAML diffs items by UID against the prior imprint and classifies each change as editorial | normative | withdrawn | renumbered (new UID). Live ConformsTo pins are NOT auto-retargeted to the new imprint.
<<<
COMMENT: >>>
KIND: requirement
BASE_UID: ARCH-CAT-IMPORT
VERSION_N: 0
rbac_op: catalog:imprint:import
priority: 55
iteration: iter-r2
security.catalog_ref: REQALM-SEC-CATALOG
security.verification_note: Catalog steward gates; standard catalogs imprint-published read-only. AC-3/CM-5 aligned. Pins are (imprint_id, item_uid).
edge: ← uses from ARCH-CAT-DRIFT
edge: ← uses from ARCH-CAT-MIGRATE
in_scope_of_contract: ReqALM product (build)
edge: → conforms_to to CM-5 (pin imprint=nist-800-53@rev5-dogfood-20261006)
edge: → conforms_to to AU-2 (pin imprint=nist-800-53@rev5-dogfood-20261006)
<<<
RELATIONS:
- TYPE: Parent
  VALUE: ARCH-CAT-IMPRINT
- TYPE: Parent
  VALUE: H03
  ROLE: Uses
- TYPE: Parent
  VALUE: ARCH-CAT-IMPRINT
  ROLE: Uses
- TYPE: Parent
  VALUE: CM-5
  ROLE: ConformsTo
- TYPE: Parent
  VALUE: AU-2
  ROLE: ConformsTo
- TYPE: Child
  VALUE: CONTRACT-ctr-reqalm-product
  ROLE: InScopeOf

[[SECTION]]
UID: ARCH-CAT-IMPORT-CHILDREN
TITLE: Children of ARCH-CAT-IMPORT

[REQUIREMENT]
UID: ARCH-CAT-DRIFT
STATUS: Active
TITLE: Catalog-drift flag on affected versions
STATEMENT: >>>
After an import diff, ReqAML marks affected requirement versions with a first-class catalog_drift field (status/flag, change_class, prior/new imprint refs) so Author/Security review UIs can queue them for action.
<<<
COMMENT: >>>
KIND: requirement
BASE_UID: ARCH-CAT-DRIFT
VERSION_N: 0
rbac_op: catalog:imprint:drift
priority: 55
iteration: iter-r2
security.catalog_ref: REQALM-SEC-CATALOG
security.verification_note: Catalog steward gates; standard catalogs imprint-published read-only. AC-3/CM-5 aligned. Pins are (imprint_id, item_uid).
edge: ← uses from ARCH-CAT-REACT
edge: ← uses from ARCH-CAT-MIGRATE
in_scope_of_contract: ReqALM product (build)
edge: → conforms_to to AU-2 (pin imprint=nist-800-53@rev5-dogfood-20261006)
edge: → conforms_to to AU-3 (pin imprint=nist-800-53@rev5-dogfood-20261006)
<<<
RELATIONS:
- TYPE: Parent
  VALUE: ARCH-CAT-IMPORT
- TYPE: Parent
  VALUE: ARCH-CAT-IMPORT
  ROLE: Uses
- TYPE: Parent
  VALUE: AU-2
  ROLE: ConformsTo
- TYPE: Parent
  VALUE: AU-3
  ROLE: ConformsTo
- TYPE: Child
  VALUE: CONTRACT-ctr-reqalm-product
  ROLE: InScopeOf

[[SECTION]]
UID: ARCH-CAT-DRIFT-CHILDREN
TITLE: Children of ARCH-CAT-DRIFT

[REQUIREMENT]
UID: ARCH-CAT-REACT
STATUS: Active
TITLE: Drift review: successor, grandfather, or withdraw
STATEMENT: >>>
Author or Security reviews catalog_drift and chooses: (a) mint a successor .N that ConformsTo the new imprint item (optional review work item), (b) keep the grandfathered pin on the prior imprint until a contract allows a bump, or (c) withdraw conformance if the control was withdrawn/gone.
<<<
COMMENT: >>>
KIND: requirement
BASE_UID: ARCH-CAT-REACT
VERSION_N: 0
rbac_op: catalog:imprint:review
priority: 55
iteration: iter-r2
security.catalog_ref: REQALM-SEC-CATALOG
security.verification_note: Catalog steward gates; standard catalogs imprint-published read-only. AC-3/CM-5 aligned. Pins are (imprint_id, item_uid).
edge: ← uses from ARCH-CAT-MIGRATE
edge: ← uses from H10
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: ARCH-CAT-DRIFT
- TYPE: Parent
  VALUE: ARCH-CAT-DRIFT
  ROLE: Uses
- TYPE: Parent
  VALUE: ARCH-CAT-PIN
  ROLE: Uses
- TYPE: Parent
  VALUE: ARCH-VER-SUCC
  ROLE: Uses
- TYPE: Parent
  VALUE: AC-3
  ROLE: ConformsTo
- TYPE: Parent
  VALUE: CM-5
  ROLE: ConformsTo
- TYPE: Child
  VALUE: CONTRACT-ctr-reqalm-product
  ROLE: InScopeOf

[[/SECTION]]

[[/SECTION]]

[[/SECTION]]

[REQUIREMENT]
UID: ARCH-CAT-SCOPE
STATUS: Active
TITLE: Project vs standard catalog imprint rules
STATEMENT: >>>
Project catalogs (REQAML-SEC-*) are steward-mutable without an imprint until publish. Standard catalogs (is_standard) always require imprint publish (H03) before pins; stewards cannot mutate published standard imprint rows in place (FIX-DENY-STEWARD-STANDARD).
<<<
COMMENT: >>>
KIND: requirement
BASE_UID: ARCH-CAT-SCOPE
VERSION_N: 0
rbac_op: catalog:imprint:scope
priority: 40
iteration: iter-r1
security.catalog_ref: REQALM-SEC-CATALOG
security.verification_note: Catalog steward gates; standard catalogs imprint-published read-only. AC-3/CM-5 aligned. Pins are (imprint_id, item_uid).
edge: ← refines from ARCH-SEC-CAT-FK
edge: ← satisfies from CAP-CATALOGS-API
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: H03
- TYPE: Parent
  VALUE: H01
  ROLE: Refines
- TYPE: Parent
  VALUE: H03
  ROLE: Refines
- TYPE: Parent
  VALUE: AC-3
  ROLE: ConformsTo
- TYPE: Parent
  VALUE: CM-5
  ROLE: ConformsTo
- TYPE: Child
  VALUE: CONTRACT-ctr-reqalm-product
  ROLE: InScopeOf

[[/SECTION]]

[REQUIREMENT]
UID: H04
STATUS: Active
TITLE: Add catalog item
STATEMENT: >>>
A steward adds a catalog entry (id + title template) to a mutable catalog. ReqAML rejects duplicate
ids and rejects adds on is_standard catalogs. The add is audited (actor, catalog_id, entry id).
<<<
COMMENT: >>>
KIND: requirement
BASE_UID: H04
VERSION_N: 0
rbac_op: catalog:entry:add
priority: 40
iteration: iter-r1
security.catalog_ref: REQALM-SEC-CATALOG
security.verification_note: Catalog steward gates; standard catalogs read-only. AC-3/CM-5 aligned.
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: SEC-CAT
- TYPE: Parent
  VALUE: AC-3
  ROLE: ConformsTo
- TYPE: Parent
  VALUE: CM-5
  ROLE: ConformsTo
- TYPE: Child
  VALUE: CONTRACT-ctr-reqalm-product
  ROLE: InScopeOf

[REQUIREMENT]
UID: H05
STATUS: Active
TITLE: Update catalog item (non-standard)
STATEMENT: >>>
A steward updates an entry in a non-standard catalog. Standard catalog entries are read-only;
ReqAML returns a conflict if the catalog is_standard (FIX-DENY-STEWARD-STANDARD). Morgan's project
steward grant on cat-reqaml-security enables the happy path (FIX-ALLOW-STEWARD-UPDATE).
<<<
COMMENT: >>>
KIND: requirement
BASE_UID: H05
VERSION_N: 0
rbac_op: catalog:entry:update
priority: 45
iteration: iter-r1
security.catalog_ref: REQALM-SEC-CATALOG
security.verification_note: Catalog steward gates; standard catalogs read-only. AC-3/CM-5 aligned.
edge: ← uses from FIX-ALLOW-STEWARD-UPDATE
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: SEC-CAT
- TYPE: Parent
  VALUE: AC-3
  ROLE: ConformsTo
- TYPE: Parent
  VALUE: CM-5
  ROLE: ConformsTo
- TYPE: Child
  VALUE: CONTRACT-ctr-reqalm-product
  ROLE: InScopeOf

[REQUIREMENT]
UID: H06
STATUS: Active
TITLE: Reference catalog via applicator-applied imprint pin (Author requests)
STATEMENT: >>>
A requirement version references a standard catalog item without copying control text (Northline). The live ConformsTo pin is applied by Security (or profile conforms_to_applicator) as (catalog_imprint_id, item_uid) — Authors request via conformance_pin_request; they do not store the pin themselves. security.catalog_ref may mirror the item_uid for browse.
<<<
COMMENT: >>>
KIND: requirement
BASE_UID: H06
VERSION_N: 0
rbac_op: catalog:entry:reference
priority: 25
iteration: iter-r0
security.catalog_ref: REQALM-SEC-CATALOG
security.verification_note: Catalog steward gates; standard catalogs imprint-published read-only. AC-3/CM-5 aligned. Pins are (imprint_id, item_uid).
edge: ← refines from ARCH-CAT-PIN
in_scope_of_contract: Design-2026-10
in_scope_of_contract: Security package
in_scope_of_contract: ReqALM product (build)
delivered_by_release: R1-core-ALM
edge: → conforms_to to AC-3 (pin imprint=nist-800-53@rev5-dogfood-20261006)
edge: → conforms_to to CM-5 (pin imprint=nist-800-53@rev5-dogfood-20261006)
<<<
RELATIONS:
- TYPE: Parent
  VALUE: SEC-CAT
- TYPE: Parent
  VALUE: D11
  ROLE: Uses
- TYPE: Parent
  VALUE: AC-3
  ROLE: ConformsTo
- TYPE: Parent
  VALUE: CM-5
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r1-core-alm
  ROLE: Delivers

[REQUIREMENT]
UID: H07
STATUS: Active
TITLE: Copy non-standard template into project line
STATEMENT: >>>
An Author copies a non-standard catalog template into a new project requirement line. ReqAML creates
a line+version with statement seeded from the template; further edits are ordinary version succession.
<<<
COMMENT: >>>
KIND: requirement
BASE_UID: H07
VERSION_N: 0
rbac_op: catalog:entry:copy
priority: 45
iteration: iter-r1
security.catalog_ref: REQALM-SEC-CATALOG
security.verification_note: Catalog steward gates; standard catalogs read-only. AC-3/CM-5 aligned.
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: SEC-CAT
- TYPE: Parent
  VALUE: AC-3
  ROLE: ConformsTo
- TYPE: Parent
  VALUE: CM-5
  ROLE: ConformsTo
- TYPE: Child
  VALUE: CONTRACT-ctr-reqalm-product
  ROLE: InScopeOf

[REQUIREMENT]
UID: H08
STATUS: Active
TITLE: Deprecate catalog item
STATEMENT: >>>
A steward deprecates a catalog item. ReqAML marks the entry deprecated for browse UI; existing
requirement catalog_ref links remain valid. Deprecation is audited and forbidden on locked standard
entry rewrite paths.
<<<
COMMENT: >>>
KIND: requirement
BASE_UID: H08
VERSION_N: 0
rbac_op: catalog:entry:deprecate
priority: 55
iteration: iter-r2
security.catalog_ref: REQALM-SEC-CATALOG
security.verification_note: Catalog steward gates; standard catalogs read-only. AC-3/CM-5 aligned.
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: SEC-CAT
- TYPE: Parent
  VALUE: AC-3
  ROLE: ConformsTo
- TYPE: Parent
  VALUE: CM-5
  ROLE: ConformsTo
- TYPE: Child
  VALUE: CONTRACT-ctr-reqalm-product
  ROLE: InScopeOf

[REQUIREMENT]
UID: H09
STATUS: Active
TITLE: Browse catalogs at current scope
STATEMENT: >>>
A Reader browses catalogs available at the current Scoped View (global + client + project).
ReqAML merges visible catalogs without exposing other clients' project catalogs.
<<<
COMMENT: >>>
KIND: requirement
BASE_UID: H09
VERSION_N: 0
rbac_op: catalog:browse
priority: 30
iteration: iter-r0
security.catalog_ref: REQALM-SEC-CATALOG
security.verification_note: Catalog steward gates; standard catalogs read-only. AC-3/CM-5 aligned.
edge: ← refines from ARCH-CAT-VISIBILITY
edge: ← refines from ARCH-BROWSE-ROADMAP
edge: ← satisfies from CAP-CATALOGS-API
in_scope_of_contract: Design-2026-10
in_scope_of_contract: ReqALM product (build)
delivered_by_release: R1-core-ALM
edge: → conforms_to to AC-3 (pin imprint=nist-800-53@rev5-dogfood-20261006)
edge: → conforms_to to CM-5 (pin imprint=nist-800-53@rev5-dogfood-20261006)
<<<
RELATIONS:
- TYPE: Parent
  VALUE: SEC-CAT
- TYPE: Parent
  VALUE: AC-3
  ROLE: ConformsTo
- TYPE: Parent
  VALUE: CM-5
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: H10
STATUS: Active
TITLE: Migrate pins: applicator apply; locked=mint_kind=pin + gate_signoff
STATEMENT: >>>
Security steward (or bound conforms_to_applicator) migrates ConformsTo pins to a new catalog imprint (whole imprint) or a single catalog item at a chosen hierarchy scope: requirement version, section (line subtree), document, project, or client. Authors may request migrate; they do not apply. ReqAML always runs a mandatory dry-run preview (editorial|normative|withdrawn|renumbered) before apply — no silent auto-retarget. Locked pins migrate only via mint_kind=pin successor .N; draft may retarget in-place after accept. Locked migrate requires Steward/Security gate plus AO gate_signoff then re-approve; audited (actor, scope, imprint_from/to, accept).
<<<
COMMENT: >>>
KIND: requirement
BASE_UID: H10
VERSION_N: 0
rbac_op: catalog:imprint:migrate
priority: 55
iteration: iter-r2
security.catalog_ref: REQALM-SEC-CATALOG
security.verification_note: Catalog steward gates; standard catalogs imprint-published read-only. AC-3/CM-5 aligned. Pins are (imprint_id, item_uid). Migrate requires preview accept + Steward/Security gate; audited.
edge: ← refines from ARCH-CAT-MIGRATE
in_scope_of_contract: ReqALM product (build)
edge: → conforms_to to AC-3 (pin imprint=nist-800-53@rev5-dogfood-20261006)
edge: → conforms_to to CM-5 (pin imprint=nist-800-53@rev5-dogfood-20261006)
edge: → conforms_to to AU-2 (pin imprint=nist-800-53@rev5-dogfood-20261006)
<<<
RELATIONS:
- TYPE: Parent
  VALUE: SEC-CAT
- TYPE: Parent
  VALUE: ARCH-CAT-REACT
  ROLE: Uses
- TYPE: Parent
  VALUE: H03
  ROLE: Uses
- TYPE: Parent
  VALUE: AC-3
  ROLE: ConformsTo
- TYPE: Parent
  VALUE: CM-5
  ROLE: ConformsTo
- TYPE: Parent
  VALUE: AU-2
  ROLE: ConformsTo
- TYPE: Child
  VALUE: CONTRACT-ctr-reqalm-product
  ROLE: InScopeOf

[[SECTION]]
UID: H10-CHILDREN
TITLE: Children of H10

[REQUIREMENT]
UID: ARCH-CAT-MIGRATE
STATUS: Active
TITLE: Migrate pins: preview, .N for locked, in-place drafts
STATEMENT: >>>
Migrate-to-imprint apply rules (locked decision): (1) Preview is mandatory — classify each affected pin's item change as editorial | normative | withdrawn | renumbered; the operator must accept before apply (dry-run; no silent apply). (2) Locked requirement versions — DERIVED (no first-class flag): a version is locked when status≠draft AND (referenced by any contract.in_scope_of OR any release.delivers). Locked pins migrate only by minting successor .N versions that ConformsTo the new (imprint_id, item_uid); never rewrite the frozen version in place. (3) Draft / unlocked versions may retarget the pin in place after preview accept (still no auto without accept). (4) Steward/Security gates apply; AO may approve-only on locked migrate (permission-tree); migration is audited. Aligns with catalog_imprints, conforms_to.catalog_imprint_id, catalog_drift, and ARCH-LOCKED Locked migrate uses mint_kind=pin successor (ARCH-MINT-KIND); clears approval; requires gate_signoff then re-approve (ARCH-GATE-SIGNOFF).
<<<
COMMENT: >>>
KIND: requirement
BASE_UID: ARCH-CAT-MIGRATE
VERSION_N: 0
rbac_op: catalog:imprint:migrate:apply
priority: 55
iteration: iter-r2
security.catalog_ref: REQALM-SEC-CATALOG
security.verification_note: Catalog steward gates; standard catalogs imprint-published read-only. AC-3/CM-5 aligned. Pins are (imprint_id, item_uid). Migrate requires preview accept + Steward/Security gate; audited.
in_scope_of_contract: ReqALM product (build)
edge: → conforms_to to AC-3 (pin imprint=nist-800-53@rev5-dogfood-20261006)
edge: → conforms_to to CM-5 (pin imprint=nist-800-53@rev5-dogfood-20261006)
edge: → conforms_to to AU-2 (pin imprint=nist-800-53@rev5-dogfood-20261006)
edge: → conforms_to to AU-12 (pin imprint=nist-800-53@rev5-dogfood-20261006)
<<<
RELATIONS:
- TYPE: Parent
  VALUE: H10
- TYPE: Parent
  VALUE: H10
  ROLE: Refines
- TYPE: Parent
  VALUE: ARCH-CAT-DRIFT
  ROLE: Uses
- TYPE: Parent
  VALUE: ARCH-CAT-REACT
  ROLE: Uses
- TYPE: Parent
  VALUE: ARCH-CAT-IMPORT
  ROLE: Uses
- TYPE: Parent
  VALUE: ARCH-CAT-PIN
  ROLE: Uses
- TYPE: Parent
  VALUE: ARCH-CAT-FREEZE
  ROLE: Uses
- TYPE: Parent
  VALUE: ARCH-VER-SUCC
  ROLE: Uses
- TYPE: Parent
  VALUE: H03
  ROLE: Uses
- TYPE: Parent
  VALUE: AC-3
  ROLE: ConformsTo
- TYPE: Parent
  VALUE: CM-5
  ROLE: ConformsTo
- TYPE: Parent
  VALUE: AU-2
  ROLE: ConformsTo
- TYPE: Parent
  VALUE: AU-12
  ROLE: ConformsTo
- TYPE: Child
  VALUE: CONTRACT-ctr-reqalm-product
  ROLE: InScopeOf

[[/SECTION]]

[REQUIREMENT]
UID: ARCH-LOCKED
STATUS: Active
TITLE: Derived locked rule for migrate (in_scope/delivers/non-draft)
STATEMENT: >>>
Locked is a DERIVED rule (no first-class flag in v1): requirement_version is locked for catalog migrate when status ≠ draft AND (uid appears in any contract.in_scope_of OR any release.delivers). Locked pins migrate only via successor .N (ARCH-CAT-MIGRATE / H10). Draft or unlocked may retarget in place after preview accept Locked migrate uses mint_kind=pin successor (ARCH-MINT-KIND); clears approval; requires gate_signoff then re-approve (ARCH-GATE-SIGNOFF).
<<<
COMMENT: >>>
KIND: requirement
BASE_UID: ARCH-LOCKED
VERSION_N: 0
rbac_op: catalog:imprint:locked_rule
priority: 25
iteration: iter-r1
security.catalog_ref: CM-3
security.verification_note: Derived lock; CM-3 change control on in_scope/delivers pins.
edge: ← refines from ARCH-ATTACH-PIN-VERSION
edge: ← refines from ARCH-ATTACH-PIN-VERSION.1
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-CAT
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: ARCH-CAT-EXTERNAL
STATUS: Active
TITLE: Catalogs represented outside project tree
STATEMENT: >>>
Standard and custom catalogs (NIST 800-53, STIG, project REQALM-SEC-*) shall live outside the project requirement tree while remaining first-class: imprints, item UIDs, and ConformsTo pins are referenced, not copied, into project data.
<<<
COMMENT: >>>
KIND: requirement
BASE_UID: ARCH-CAT-EXTERNAL
VERSION_N: 0
rbac_op: catalog:browse
priority: 15
iteration: iter-r1
security.catalog_ref: CM-2
security.verification_note: Groomed 2026-10-09; pre-write or UI track.
edge: ← refines from ARCH-CAT-PROJECT-ROLLUP
edge: ← satisfies from CAP-UI-VIEW-CATALOG
in_scope_of_contract: ReqALM product (build)
<<<
RELATIONS:
- TYPE: Parent
  VALUE: SEC-CAT
- TYPE: Parent
  VALUE: ARCH-CAT-IMPRINT
  ROLE: Refines
- TYPE: Child
  VALUE: CONTRACT-ctr-reqalm-product
  ROLE: InScopeOf

[REQUIREMENT]
UID: ARCH-CAT-PROJECT-ROLLUP
STATUS: Active
TITLE: Catalog control project rollup
STATEMENT: >>>
For catalog controls in scope of a project, a control shall show incomplete for the project when any in-scope capability or requirement relying on that control is incomplete or needs re-check. Rollup shall not require duplicating catalog text in the project tree.
<<<
COMMENT: >>>
KIND: requirement
BASE_UID: ARCH-CAT-PROJECT-ROLLUP
VERSION_N: 0
rbac_op: catalog:browse
priority: 15
iteration: iter-r1
security.catalog_ref: CM-2
security.verification_note: Groomed 2026-10-09; pre-write or UI track.
in_scope_of_contract: ReqALM product (build)
<<<
RELATIONS:
- TYPE: Parent
  VALUE: SEC-CAT
- TYPE: Parent
  VALUE: ARCH-CAT-EXTERNAL
  ROLE: Refines
- TYPE: Child
  VALUE: CONTRACT-ctr-reqalm-product
  ROLE: InScopeOf

[REQUIREMENT]
UID: ARCH-CAT-VISIBILITY
STATUS: Active
TITLE: User-selected visible catalogs
STATEMENT: >>>
The user shall choose which catalogs are visible in browse and trace views per user per project; the selection shall persist in server-side session or profile state keyed by (identity_id, project_id). The default when unset shall be all catalogs that have at least one conforms_to or catalog link in the project. Hidden catalogs shall not appear in control rollups or two-column catalog views until selected.
<<<
COMMENT: >>>
KIND: requirement
BASE_UID: ARCH-CAT-VISIBILITY
VERSION_N: 0
rbac_op: catalog:browse
priority: 15
iteration: iter-r1
security.catalog_ref: CM-2
security.verification_note: Groomed 2026-10-09; pre-write or UI track.
edge: ← satisfies from CAP-UI-VIEW-CATALOG
in_scope_of_contract: ReqALM product (build)
<<<
RELATIONS:
- TYPE: Parent
  VALUE: SEC-CAT
- TYPE: Parent
  VALUE: H09
  ROLE: Refines
- TYPE: Child
  VALUE: CONTRACT-ctr-reqalm-product
  ROLE: InScopeOf

[REQUIREMENT]
UID: ARCH-SEC-CAT-FK
STATUS: Active
TITLE: catalog_defs.project_id FK
STATEMENT: >>>
catalog_defs.project_id shall reference projects(id) with a foreign key when project-scoped catalogs are stored. Parallel PR #33 migration 010 delivers this constraint.
<<<
COMMENT: >>>
KIND: requirement
BASE_UID: ARCH-SEC-CAT-FK
VERSION_N: 0
priority: 15
iteration: iter-r1
security.catalog_ref: CM-6
security.verification_note: Groomed 2026-10-09; pre-write or UI track.
in_scope_of_contract: ReqALM product (build)
<<<
RELATIONS:
- TYPE: Parent
  VALUE: SEC-CAT
- TYPE: Parent
  VALUE: ARCH-CAT-SCOPE
  ROLE: Refines
- TYPE: Child
  VALUE: CONTRACT-ctr-reqalm-product
  ROLE: InScopeOf

[REQUIREMENT]
UID: ARCH-SEC-CAT-LABEL-IMPRINT
STATUS: Active
TITLE: Catalog labels keyed per imprint
STATEMENT: >>>
Catalog item labels shall be keyed per imprint (catalog_imprint_id + item_uid), not per catalog id alone, so imprint succession does not collide titles.
<<<
COMMENT: >>>
KIND: requirement
BASE_UID: ARCH-SEC-CAT-LABEL-IMPRINT
VERSION_N: 0
priority: 15
iteration: iter-r1
security.catalog_ref: CM-6
security.verification_note: Groomed 2026-10-09; pre-write or UI track.
in_scope_of_contract: ReqALM product (build)
<<<
RELATIONS:
- TYPE: Parent
  VALUE: SEC-CAT
- TYPE: Parent
  VALUE: ARCH-CAT-PIN
  ROLE: Refines
- TYPE: Child
  VALUE: CONTRACT-ctr-reqalm-product
  ROLE: InScopeOf

[REQUIREMENT]
UID: CAP-CATALOGS-API
STATUS: Active
TITLE: Read catalogs and controls (catalogs API)
STATEMENT: >>>
Grant-scoped read-only catalogs API under /api/v1/projects/:projectId/catalogs: list visible catalogs with imprints (version label, status); paged controls for an imprint (id, title, family, conforming_count scoped to the project); control detail (title, statement text, conforming project lines with direct or version-pin link). Private catalogs 404 like unknown without a grant on the owning project. Dogfood seed loads catalog metadata, imprint labels, and conforms_to trace edges.
<<<
COMMENT: >>>
KIND: capability
BASE_UID: CAP-CATALOGS-API
VERSION_N: 0
priority: 10
iteration: iter-r1
security.catalog_ref: AC-3
security.verification_note: Shipped with catalogs read API PR #33 (merge ed372358fb1a04546ea884c9cbcee69f959517b1).
edge: ← satisfies from CAP-BROWSE-UI-CATALOGS
in_scope_of_contract: ReqALM product (build)
delivered_by_release: R1 — catalogs read API
<<<
RELATIONS:
- TYPE: Parent
  VALUE: SEC-CAT
- TYPE: Parent
  VALUE: H09
  ROLE: Satisfies
- TYPE: Parent
  VALUE: ARCH-CAT-SCOPE
  ROLE: Satisfies
- TYPE: Parent
  VALUE: ARCH-API-RBAC
  ROLE: Satisfies
- TYPE: Parent
  VALUE: CAP-READ-REQS
  ROLE: Satisfies
- TYPE: Parent
  VALUE: CAP-SVC-OPERATION-ROUTE
  ROLE: Satisfies
- TYPE: Parent
  VALUE: C08
  ROLE: Satisfies
- TYPE: Child
  VALUE: CONTRACT-ctr-reqalm-product
  ROLE: InScopeOf
- TYPE: Child
  VALUE: RELEASE-rel-r1-catalogs-api
  ROLE: Delivers

[[/SECTION]]

[[SECTION]]
UID: SEC-CAP
TITLE: Capabilities & Artifacts

[TEXT]
UID: SEC-CAP-INTRO
STATEMENT: >>>
Capability packs and attached design artifacts (sequences, C4, mockups, OpenAPI) group how requirements are satisfied in the product.
<<<

[REQUIREMENT]
UID: I01
STATUS: Active
TITLE: Create capability line
STATEMENT: >>>
An Author creates a capability-kind line (CapabilityLine SubjectKind) together with at least one Satisfies edge to a target requirement version in the same mutation (ARCH-CAP-LINK / gate-satisfies-at-create). Orphan capabilities without Satisfies are denied. UI coaches link quality before approve (ARCH-CAP-APPROVE).
<<<
COMMENT: >>>
KIND: requirement
BASE_UID: I01
VERSION_N: 0
rbac_op: capability:create
priority: 25
iteration: iter-r0
security.catalog_ref: AC-3
security.verification_note: AC-3 access enforcement; AU-2/3/12 where mutating.
edge: ← satisfies from CAP-UI-VIEW-CAP-DETAIL
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CAP
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: I02
STATUS: Active
TITLE: Link capability satisfies requirement
STATEMENT: >>>
An Author links a capability version to a requirement via satisfies (see also E04). ReqAML ensures
the edge is the coverage record used by packs and future regression beds.
<<<
COMMENT: >>>
KIND: requirement
BASE_UID: I02
VERSION_N: 0
rbac_op: capability:satisfies
priority: 20
iteration: iter-r0
security.catalog_ref: AC-3
security.verification_note: AC-3 access enforcement; AU-2/3/12 where mutating.
edge: ← uses from E04
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CAP
- TYPE: Parent
  VALUE: E04
  ROLE: Refines
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: I03
STATUS: Active
TITLE: Attach artifact URI
STATEMENT: >>>
An Author attaches an artifact (OpenAPI, wireframe, mock, other) URI to a capability or architecture
version. ReqAML stores kind+uri rows; URIs should point at repo-relative design assets when possible.
<<<
COMMENT: >>>
KIND: requirement
BASE_UID: I03
VERSION_N: 0
rbac_op: capability:artifact:attach
priority: 30
iteration: iter-r0
security.catalog_ref: AC-3
security.verification_note: AC-3 access enforcement; AU-2/3/12 where mutating.
edge: ← satisfies from CAP-UI-VIEW-CAP-DETAIL
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CAP
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: I04
STATUS: Active
TITLE: Update / replace artifact URI
STATEMENT: >>>
An Author updates or replaces an artifact URI on a version. ReqAML audits before/after URI; kind may
stay the same. Invalid URIs fail validation (SI-10) before persistence.
<<<
COMMENT: >>>
KIND: requirement
BASE_UID: I04
VERSION_N: 0
rbac_op: capability:artifact:update
priority: 45
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CAP
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: I05
STATUS: Active
TITLE: Remove artifact
STATEMENT: >>>
An Author removes an artifact attachment. ReqAML deletes the artifact row; the capability version
remains. The removal is audited (actor, capability UID, prior URI). Downstream packs that referenced the
URI must re-attach if still needed.
<<<
COMMENT: >>>
KIND: requirement
BASE_UID: I05
VERSION_N: 0
rbac_op: capability:artifact:remove
priority: 50
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CAP
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: I06
STATUS: Active
TITLE: View capability pack grouping
STATEMENT: >>>
A Reader views capability pack / regression-bed grouping (later). ReqAML returns capabilities with
their satisfies edges and artifacts for pack review; full regression automation is deferred.
<<<
COMMENT: >>>
KIND: requirement
BASE_UID: I06
VERSION_N: 0
rbac_op: capability:pack:view
priority: 70
iteration: iter-r2
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CAP
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: CAP-TREE
STATUS: Active
TITLE: Requirement tree editing pack
STATEMENT: >>>
Capability pack covering line create/move/reorder, tree views, and search for the requirements shell
(mockup 01). Authors mutate structure under project grants; Readers expand/collapse and search within
Client Scoped View. All structure mutations audit actor and affected base_uid.
<<<
COMMENT: >>>
KIND: capability
BASE_UID: CAP-TREE
VERSION_N: 0
priority: 15
iteration: iter-r0
security.catalog_ref: AC-3
security.verification_note: AC-3 access enforcement; AU-2/3/12 where mutating.
in_scope_of_contract: Design-2026-10
in_scope_of_contract: Platform baseline
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CAP
- TYPE: Parent
  VALUE: C01
  ROLE: Satisfies
- TYPE: Parent
  VALUE: C06
  ROLE: Satisfies
- TYPE: Parent
  VALUE: C08
  ROLE: Satisfies
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r1-core-alm
  ROLE: Delivers

[REQUIREMENT]
UID: CAP-CONTRACT-UI.1
STATUS: Draft
TITLE: Contracts & document view pack
STATEMENT: >>>
Planned capability pack for contract list/detail and document view (not built on main). Layout intent when implemented: contracts list with overlap timeline and in_scope_of counts; detail with membership linking to requirement versions; document view built from in_scope_of uids with optional context-parent walk. Reference mockups in repo: 02-contracts-list-detail.jpg, 03-document-view-from-contract.jpg.
<<<
COMMENT: >>>
KIND: capability
BASE_UID: CAP-CONTRACT-UI
VERSION_N: 1
priority: 15
iteration: iter-r0
security.catalog_ref: AC-3
security.verification_note: Draft .1 layout intent; active CAP-CONTRACT-UI unchanged until contract UI ships.
<<<
RELATIONS:
- TYPE: Parent
  VALUE: SEC-CAP
- TYPE: Parent
  VALUE: CAP-CONTRACT-UI
  ROLE: Refines

[REQUIREMENT]
UID: CAP-CONTRACT-UI
STATUS: Active
TITLE: Contracts & document view pack
STATEMENT: >>>
Capability pack for contract list/detail and document view from contract (mockups 02–03).
Document view builds from in_scope_of version UIDs with optional context-parent walk. Closed contracts
freeze membership; Readers still open document views read-only.
<<<
COMMENT: >>>
KIND: capability
BASE_UID: CAP-CONTRACT-UI
VERSION_N: 0
priority: 15
iteration: iter-r0
security.catalog_ref: AC-3
security.verification_note: AC-3 access enforcement; AU-2/3/12 where mutating.
edge: ← refines from CAP-CONTRACT-UI.1
edge: ← satisfies from CAP-BROWSE-UI-CONTRACTS
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CAP
- TYPE: Parent
  VALUE: F01
  ROLE: Satisfies
- TYPE: Parent
  VALUE: F07
  ROLE: Satisfies
- TYPE: Parent
  VALUE: F10
  ROLE: Satisfies
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: CAP-VERSION-UI.1
STATUS: Draft
TITLE: Version lineage pack
STATEMENT: >>>
Planned capability pack for version succession, lineage, and compare UX (not built on main). Layout intent when implemented: lineage strip across obsolete → active → draft tips; compare with field-level diffs; successor mint actions on detail header. Reference mockup in repo: 04-requirement-lineage-versions.jpg.
<<<
COMMENT: >>>
KIND: capability
BASE_UID: CAP-VERSION-UI
VERSION_N: 1
priority: 15
iteration: iter-r0
security.catalog_ref: AC-3
security.verification_note: Draft .1 layout intent; active CAP-VERSION-UI unchanged until version UI ships.
<<<
RELATIONS:
- TYPE: Parent
  VALUE: SEC-CAP
- TYPE: Parent
  VALUE: CAP-VERSION-UI
  ROLE: Refines

[REQUIREMENT]
UID: CAP-VERSION-UI
STATUS: Active
TITLE: Version lineage pack
STATEMENT: >>>
Capability pack for version succession, lineage, and compare UX (mockup 04). Authors create
successors; published tips are immutable and require .N+1 for edits. Compare shows field-level diffs used
by FIX-COMPARE-2HOP across multi-hop lineages.
<<<
COMMENT: >>>
KIND: capability
BASE_UID: CAP-VERSION-UI
VERSION_N: 0
priority: 15
iteration: iter-r0
security.catalog_ref: AC-3
security.verification_note: AC-3 access enforcement; AU-2/3/12 where mutating.
edge: ← refines from CAP-VERSION-UI.1
in_scope_of_contract: Design-2026-10
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-CAP
- TYPE: Parent
  VALUE: D02
  ROLE: Satisfies
- TYPE: Parent
  VALUE: D06
  ROLE: Satisfies
- TYPE: Parent
  VALUE: D07
  ROLE: Satisfies
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-ctr-reqalm-product
  ROLE: InScopeOf
- TYPE: Child
  VALUE: RELEASE-rel-r1-core-alm
  ROLE: Delivers

[REQUIREMENT]
UID: CAP-UPKEEP-MONTHLY-SEC-AUDIT
STATUS: Draft
TITLE: Monthly security audit (planned)
STATEMENT: >>>
PLANNED capability (not shipped). Each month, Security performs a documented ReqALM security audit: auth/session anomalies, privileged use, configuration drift vs approved baseline, and open findings from the prior cycle. Results are recorded and remediated.
<<<
COMMENT: >>>
KIND: capability
BASE_UID: CAP-UPKEEP-MONTHLY-SEC-AUDIT
VERSION_N: 0
priority: 50
iteration: iter-r1
security.catalog_ref: CA-7
security.verification_note: Planned upkeep capability — not shipped; no verification outcome.
in_scope_of_contract: ReqALM maintenance
edge: → conforms_to to CA-7 (pin imprint=nist-800-53@rev5-dogfood-20261006)
<<<
RELATIONS:
- TYPE: Parent
  VALUE: SEC-CAP
- TYPE: Parent
  VALUE: SYS-CYBER-UPKEEP
  ROLE: Satisfies
- TYPE: Parent
  VALUE: CA-7
  ROLE: ConformsTo
- TYPE: Child
  VALUE: CONTRACT-ctr-reqalm-maintenance
  ROLE: InScopeOf

[REQUIREMENT]
UID: CAP-UPKEEP-MONTHLY-DEPS-VULN
STATUS: Draft
TITLE: Monthly dependency and vulnerability review (planned)
STATEMENT: >>>
PLANNED capability (not shipped). Each month, review application and container dependency manifests for known vulnerabilities (SCA), triage by severity, and plan patches or Security-approved risk acceptance before the next review.
<<<
COMMENT: >>>
KIND: capability
BASE_UID: CAP-UPKEEP-MONTHLY-DEPS-VULN
VERSION_N: 0
priority: 50
iteration: iter-r1
security.catalog_ref: RA-5
security.verification_note: Planned upkeep capability — not shipped; no verification outcome.
in_scope_of_contract: ReqALM maintenance
edge: → conforms_to to RA-5 (pin imprint=nist-800-53@rev5-dogfood-20261006)
edge: → conforms_to to SI-2 (pin imprint=nist-800-53@rev5-dogfood-20261006)
<<<
RELATIONS:
- TYPE: Parent
  VALUE: SEC-CAP
- TYPE: Parent
  VALUE: SYS-CYBER-UPKEEP
  ROLE: Satisfies
- TYPE: Parent
  VALUE: RA-5
  ROLE: ConformsTo
- TYPE: Parent
  VALUE: SI-2
  ROLE: ConformsTo
- TYPE: Child
  VALUE: CONTRACT-ctr-reqalm-maintenance
  ROLE: InScopeOf

[REQUIREMENT]
UID: CAP-UPKEEP-QUARTERLY-ACCESS-RECERT
STATUS: Draft
TITLE: Quarterly access recertification (planned)
STATEMENT: >>>
PLANNED capability (not shipped). Quarterly, an Authorizing Official or delegate recertifies ReqALM project grants and privileged roles: confirm least privilege, remove stale grants, audit the decision.
<<<
COMMENT: >>>
KIND: capability
BASE_UID: CAP-UPKEEP-QUARTERLY-ACCESS-RECERT
VERSION_N: 0
priority: 50
iteration: iter-r1
security.catalog_ref: AC-2
security.verification_note: Planned upkeep capability — not shipped; no verification outcome.
in_scope_of_contract: ReqALM maintenance
edge: → conforms_to to AC-2 (pin imprint=nist-800-53@rev5-dogfood-20261006)
<<<
RELATIONS:
- TYPE: Parent
  VALUE: SEC-CAP
- TYPE: Parent
  VALUE: SYS-CYBER-UPKEEP
  ROLE: Satisfies
- TYPE: Parent
  VALUE: AC-2
  ROLE: ConformsTo
- TYPE: Child
  VALUE: CONTRACT-ctr-reqalm-maintenance
  ROLE: InScopeOf

[REQUIREMENT]
UID: CAP-UPKEEP-AUDIT-LOG-REVIEW
STATUS: Draft
TITLE: Audit log review (planned)
STATEMENT: >>>
PLANNED capability (not shipped). Review exported OTEL/security audit streams for suspicious patterns, failed auth spikes, and privileged mutations; escalate per incident response policy.
<<<
COMMENT: >>>
KIND: capability
BASE_UID: CAP-UPKEEP-AUDIT-LOG-REVIEW
VERSION_N: 0
priority: 50
iteration: iter-r1
security.catalog_ref: AU-6
security.verification_note: Planned upkeep capability — not shipped; no verification outcome.
in_scope_of_contract: ReqALM maintenance
edge: → conforms_to to AU-6 (pin imprint=nist-800-53@rev5-dogfood-20261006)
<<<
RELATIONS:
- TYPE: Parent
  VALUE: SEC-CAP
- TYPE: Parent
  VALUE: SYS-CYBER-UPKEEP
  ROLE: Satisfies
- TYPE: Parent
  VALUE: AU-6
  ROLE: ConformsTo
- TYPE: Child
  VALUE: CONTRACT-ctr-reqalm-maintenance
  ROLE: InScopeOf

[[/SECTION]]

[[SECTION]]
UID: SEC-WI
TITLE: Work Items & Sync

[TEXT]
UID: SEC-WI-INTRO
STATEMENT: >>>
Work-item sync bridges requirement versions to external trackers: create, map, push/pull fields, conflict resolution, and disconnect.
<<<

[REQUIREMENT]
UID: J01
STATUS: Active
TITLE: Mark requirement ready for work item
STATEMENT: >>>
An Author marks a requirement version ready for work-item creation by setting grooming_state=wi_ready (same field advanced by K03). ReqAML records readiness metadata used by J02; it does not create the external ticket yet.
<<<
COMMENT: >>>
KIND: requirement
BASE_UID: J01
VERSION_N: 0
rbac_op: workitem:mark_ready
priority: 30
iteration: iter-r1
security.catalog_ref: AC-3
security.verification_note: AC-3 access enforcement; AU-2/3/12 where mutating.
edge: ← uses from K03
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-WI
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: J02
STATUS: Active
TITLE: Create work item from requirement version
STATEMENT: >>>
An Author or Developer creates an external work item from a requirement version. ReqAML stores the
link mapping (external id, system) and seeds the ticket summary from the statement.
<<<
COMMENT: >>>
KIND: requirement
BASE_UID: J02
VERSION_N: 0
rbac_op: workitem:create
priority: 25
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-WI
- TYPE: Parent
  VALUE: D04
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: J03
STATUS: Active
TITLE: Update work item link mapping
STATEMENT: >>>
An Author updates the mapping between a requirement version and an external work item id.
ReqAML audits remaps; orphaned external tickets are not auto-deleted.
<<<
COMMENT: >>>
KIND: requirement
BASE_UID: J03
VERSION_N: 0
rbac_op: workitem:remap
priority: 45
iteration: iter-r2
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-WI
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: J04
STATUS: Active
TITLE: Push field changes req → work item
STATEMENT: >>>
An Author pushes selected field changes from a requirement version to the linked work item.
ReqAML records last-push timestamp and which fields synced.
<<<
COMMENT: >>>
KIND: requirement
BASE_UID: J04
VERSION_N: 0
rbac_op: workitem:push
priority: 40
iteration: iter-r2
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-WI
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: J05
STATUS: Active
TITLE: Pull field changes work item → req
STATEMENT: >>>
An Author pulls selected fields from the work item back into a draft requirement successor when needed.
Pull into active immutable versions is rejected; succession rules apply.
<<<
COMMENT: >>>
KIND: requirement
BASE_UID: J05
VERSION_N: 0
rbac_op: workitem:pull
priority: 40
iteration: iter-r2
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-WI
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: J06
STATUS: Active
TITLE: Resolve sync conflict
STATEMENT: >>>
When push/pull detects conflicting edits, an Author resolves the conflict by choosing req, work item,
or manual merge into a new draft successor. ReqAML audits the resolution choice.
<<<
COMMENT: >>>
KIND: requirement
BASE_UID: J06
VERSION_N: 0
rbac_op: workitem:conflict_resolve
priority: 50
iteration: iter-r2
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-WI
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: J07
STATUS: Active
TITLE: View sync status / last sync
STATEMENT: >>>
A Reader views sync status and last sync timestamps for a requirement–work-item link.
ReqAML returns link state, last push/pull times, and any unresolved conflict flag without exposing
external system credentials. Missing links return an empty status, not an error.
<<<
COMMENT: >>>
KIND: requirement
BASE_UID: J07
VERSION_N: 0
rbac_op: workitem:status
priority: 45
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-WI
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: J08
STATUS: Active
TITLE: Disconnect work item link
STATEMENT: >>>
An Author disconnects a work-item link. ReqAML removes the mapping and audits the disconnect;
the external work item is left unchanged. Subsequent push/pull against the version fails until remapped.
<<<
COMMENT: >>>
KIND: requirement
BASE_UID: J08
VERSION_N: 0
rbac_op: workitem:disconnect
priority: 50
iteration: iter-r2
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-WI
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[[/SECTION]]

[[SECTION]]
UID: SEC-GROOM
TITLE: Grooming & Agile Flow

[TEXT]
UID: SEC-GROOM-INTRO
STATEMENT: >>>
Grooming flow turns priority leaves into detailed, WI-ready requirements via parent detail-debt walks and iteration assignment.
<<<

[REQUIREMENT]
UID: K01
STATUS: Active
TITLE: Open priority queue
STATEMENT: >>>
An Author opens the priority queue (“what to groom next”). ReqAML returns versions with priority set,
sorted for grooming, filtered by Scoped View and project.
<<<
COMMENT: >>>
KIND: requirement
BASE_UID: K01
VERSION_N: 0
rbac_op: groom:queue
priority: 20
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-GROOM
- TYPE: Parent
  VALUE: D08
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: K02
STATUS: Active
TITLE: Walk parent detail-debt
STATEMENT: >>>
From a priority leaf, an Author walks parent detail-debt to see which ancestors need richer statements
before the leaf is WI-ready. ReqAML returns ancestor versions lacking detail markers.
<<<
COMMENT: >>>
KIND: requirement
BASE_UID: K02
VERSION_N: 0
rbac_op: groom:detail_debt
priority: 30
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-GROOM
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: K03
STATUS: Active
TITLE: Advance grooming state
STATEMENT: >>>
An Author advances grooming_state on a requirement_version along want → detailed → wi_ready. ReqAML stores grooming_state on the version and audits transitions. J01 (mark WI-ready) is the terminal advance to wi_ready; work-item create (J02) expects wi_ready.
<<<
COMMENT: >>>
KIND: requirement
BASE_UID: K03
VERSION_N: 0
rbac_op: groom:advance
priority: 25
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-GROOM
- TYPE: Parent
  VALUE: J01
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: K04
STATUS: Active
TITLE: Assign iteration / sprint
STATEMENT: >>>
An Author assigns an iteration/sprint on a version during grooming (overlaps D09). ReqAML validates
project membership of the iteration.
<<<
COMMENT: >>>
KIND: requirement
BASE_UID: K04
VERSION_N: 0
rbac_op: groom:assign_iteration
priority: 30
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-GROOM
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: K05
STATUS: Active
TITLE: View work track by iteration
STATEMENT: >>>
A Reader views the work track for an iteration — versions assigned to that window with grooming state
and priorities. Data is scoped to the bound client/project. This is a read model over existing version
fields; it does not invent a separate planning store.
<<<
COMMENT: >>>
KIND: requirement
BASE_UID: K05
VERSION_N: 0
rbac_op: groom:work_track
priority: 35
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-GROOM
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: K06
STATUS: Active
TITLE: View release path vs work track
STATEMENT: >>>
A Reader compares release delivers membership against the iteration work track to spot gaps (planned vs committed). Gantt/schedule overlays are product requirements (G07 / ARCH-GANTT) used together with this gap view; backlog planning remains G04 / K01 / ARCH-BACKLOG.
<<<
COMMENT: >>>
KIND: requirement
BASE_UID: K06
VERSION_N: 0
rbac_op: groom:release_path
priority: 45
iteration: iter-r2
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-GROOM
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: ARCH-BACKLOG
STATUS: Active
TITLE: Backlog planning views (priority queues, release backlog) as product requirements
STATEMENT: >>>
Backlog planning is a first-class product capability: priority queues (K01), release backlog ordering (G04), and related grooming/work-track views. Together with ARCH-GANTT / G07 these define planning end-to-end — do not treat backlog or schedule as defer-only.
<<<
COMMENT: >>>
KIND: requirement
BASE_UID: ARCH-BACKLOG
VERSION_N: 0
rbac_op: planning:backlog
priority: 20
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-GROOM
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: CAP-BROWSE-ROADMAP
STATUS: Draft
TITLE: Browse roadmap (planned releases queue)
STATEMENT: >>>
Tracks the ordered read-only browse program under ARCH-BROWSE-ROADMAP. Each tranche is still one PR = one release (API then UI): rel-r1-catalogs-api (parallel CAP-CATALOGS-API), rel-r1-browse-ui-catalogs, rel-r1-read-planning, rel-r1-browse-ui-planning, rel-r1-read-artifacts, rel-r1-browse-ui-artifacts, rel-r1-read-workflow, rel-r1-browse-ui-workflow, rel-r1-read-access, rel-r1-browse-ui-access, rel-r1-read-audit, rel-r1-browse-ui-audit, rel-r1-browse-ui-relations (parallel), rel-r1-browse-ui-trace-views. This capability is documentation-only until the first tranche PR adds real caps.
<<<
COMMENT: >>>
KIND: capability
BASE_UID: CAP-BROWSE-ROADMAP
VERSION_N: 0
priority: 10
iteration: iter-r1
security.catalog_ref: CM-2
security.verification_note: Planned; not shipped on main.
in_scope_of_contract: ReqALM product (build)
<<<
RELATIONS:
- TYPE: Parent
  VALUE: SEC-GROOM
- TYPE: Parent
  VALUE: ARCH-BROWSE-ROADMAP
  ROLE: Satisfies
- TYPE: Child
  VALUE: CONTRACT-ctr-reqalm-product
  ROLE: InScopeOf

[REQUIREMENT]
UID: CAP-SEED-GROOMING
STATUS: Draft
TITLE: Dogfood seed grooming (requirements honesty)
STATEMENT: >>>
Documentation-only seed pass: refined architecture requirements (acceptance criteria, trace views, hierarchy, security follow-ups), browse roadmap releases, and honesty corrections in dogfood.yaml with regenerated StrictDoc out/ and HANDOFF.md. No application runtime changes.
<<<
COMMENT: >>>
KIND: capability
BASE_UID: CAP-SEED-GROOMING
VERSION_N: 0
priority: 10
iteration: iter-r1
security.catalog_ref: CM-2
security.verification_note: Planned until seed grooming PR merges.
in_scope_of_contract: ReqALM product (build)
delivered_by_release: R1 — dogfood seed grooming
<<<
RELATIONS:
- TYPE: Parent
  VALUE: SEC-GROOM
- TYPE: Parent
  VALUE: ARCH-BROWSE-ROADMAP
  ROLE: Satisfies
- TYPE: Child
  VALUE: CONTRACT-ctr-reqalm-product
  ROLE: InScopeOf
- TYPE: Child
  VALUE: RELEASE-rel-r1-seed-grooming
  ROLE: Delivers

[[/SECTION]]

[[SECTION]]
UID: SEC-IO
TITLE: Import / Export

[TEXT]
UID: SEC-IO-INTRO
STATEMENT: >>>
Import/export interchange with StrictDoc and snapshot bills of requirements. PDF/Markdown document export is deferred.
<<<

[REQUIREMENT]
UID: L01
STATUS: Active
TITLE: Import StrictDoc / notation file
STATEMENT: >>>
An Author imports a StrictDoc (.sdoc) or approved notation file into a project. ReqAML maps sections
and requirements into lines+versions without treating StrictDoc as the system of record afterward.
<<<
COMMENT: >>>
KIND: requirement
BASE_UID: L01
VERSION_N: 0
rbac_op: io:import:strictdoc
priority: 40
iteration: iter-r1
security.catalog_ref: AC-3
security.verification_note: AC-3 scoped export/import; AU-2/3/12 on interchange actions.
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-IO
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: L02
STATUS: Active
TITLE: StrictDoc export; fixture golden {A01,A02} only
STATEMENT: >>>
An Author exports a project tree or contract document view to StrictDoc interchange. ReqAML emits .sdoc suitable for external tools; Postgres remains authoritative. For contract-fixture-doc-walk with context parents off, the exported UID set must equal {A01, A02} — exactly the version UIDs in in_scope_of (FIX-EXPORT-L02-GOLDEN). Catalog item UIDs (e.g. AC-3) are NEVER members of in_scope_of; they appear only as ConformsTo pins.
<<<
COMMENT: >>>
KIND: requirement
BASE_UID: L02
VERSION_N: 0
rbac_op: io:export:strictdoc
priority: 35
iteration: iter-r0
security.catalog_ref: AC-3
security.verification_note: AC-3 scoped export/import; AU-2/3/12 on interchange actions.
edge: ← uses from FIX-EXPORT-L02-GOLDEN
in_scope_of_contract: Platform baseline
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-IO
- TYPE: Parent
  VALUE: ARCH-CONTRACT.1
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-platform-baseline
  ROLE: InScopeOf
- TYPE: Child
  VALUE: CONTRACT-ctr-reqalm-product
  ROLE: InScopeOf
- TYPE: Child
  VALUE: RELEASE-rel-r1-core-alm
  ROLE: Delivers

[REQUIREMENT]
UID: L03
STATUS: Draft
TITLE: Export document view (PDF/Markdown) — later
STATEMENT: >>>
Export of document view to PDF/Markdown is deferred past R1. This requirement records the intent
without committing R0 delivery.
<<<
COMMENT: >>>
KIND: requirement
BASE_UID: L03
VERSION_N: 0
rbac_op: io:export:document
priority: 80
iteration: iter-r2
security.catalog_ref: AC-3
security.verification_note: AC-3 scoped export/import; AU-2/3/12 on interchange actions.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-IO
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: L04
STATUS: Active
TITLE: Export snapshot bill of requirements
STATEMENT: >>>
A Release manager exports a bill of requirements for a release snapshot (delivered version UIDs +
statements). ReqAML generates a stable artifact for review packages.
<<<
COMMENT: >>>
KIND: requirement
BASE_UID: L04
VERSION_N: 0
rbac_op: io:export:snapshot
priority: 40
iteration: iter-r1
security.catalog_ref: AC-3
security.verification_note: AC-3 scoped export/import; AU-2/3/12 on interchange actions.
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-IO
- TYPE: Parent
  VALUE: ARCH-RELEASE
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: ARCH-SEC-SEED-INTEGRITY
STATUS: Active
TITLE: Seed loader base_uid and delivers integrity
STATEMENT: >>>
The dogfood seed loader shall reject a base_uid that appears in more than one project and shall reject release.delivers entries whose requirement version project_id does not match the release's project_id.
<<<
COMMENT: >>>
KIND: requirement
BASE_UID: ARCH-SEC-SEED-INTEGRITY
VERSION_N: 0
priority: 15
iteration: iter-r1
security.catalog_ref: CM-6
security.verification_note: Groomed 2026-10-09; pre-write or UI track.
in_scope_of_contract: ReqALM product (build)
<<<
RELATIONS:
- TYPE: Parent
  VALUE: SEC-IO
- TYPE: Parent
  VALUE: ARCH-DEVENV-SEED
  ROLE: Refines
- TYPE: Child
  VALUE: CONTRACT-ctr-reqalm-product
  ROLE: InScopeOf

[REQUIREMENT]
UID: ARCH-SEC-LOADER-EDGE-SYNC
STATUS: Active
TITLE: Seed loader deletes removed trace edges
STATEMENT: >>>
The seed loader shall delete trace_edges removed from the seed document on re-load (sync), not only insert new rows.
<<<
COMMENT: >>>
KIND: requirement
BASE_UID: ARCH-SEC-LOADER-EDGE-SYNC
VERSION_N: 0
priority: 15
iteration: iter-r1
security.catalog_ref: CM-6
security.verification_note: Groomed 2026-10-09; pre-write or UI track.
in_scope_of_contract: ReqALM product (build)
<<<
RELATIONS:
- TYPE: Parent
  VALUE: SEC-IO
- TYPE: Parent
  VALUE: ARCH-DEVENV-SEED
  ROLE: Refines
- TYPE: Child
  VALUE: CONTRACT-ctr-reqalm-product
  ROLE: InScopeOf

[REQUIREMENT]
UID: ARCH-FIGMA
STATUS: Draft
TITLE: Figma design links (draft)
STATEMENT: >>>
A capability or requirement version may link to Figma nodes by file key and node id (file, frame, or component). Linked ids must match ^[A-Za-z0-9]{10,128}$ (file key) and ^[0-9]+[:-][0-9]+(;[0-9]+[:-][0-9]+)*$ (node id); anything else is rejected with 400. Previews are fetched server-side from api.figma.com, rasterized to PNG, cached per project, and served same-origin as images through ARCH-ATTACH-SERVE rules (images only); the UI does not embed Figma iframes or load third-party scripts, and CSP frame-src stays 'none'. A link records the node's lastModified/version at link time; when the server observes a newer value (scheduled polling, or a Figma webhook whose signature/passcode is verified before processing), the link and its version are flagged needs re-check. Figma content returned to ReqALM is untrusted input: names are sanitized and length-capped, and nothing returned is executed or rendered as HTML.
<<<
COMMENT: >>>
KIND: requirement
BASE_UID: ARCH-FIGMA
VERSION_N: 0
rbac_op: figma:link
priority: 30
iteration: iter-r2
security.catalog_ref: SA-9
security.verification_note: Cyber 2026-10-09 attachments-figma mapping; Draft, needs-spike (SPIKE-FIGMA-FEASIBILITY); external service integration. Figma is an external system (AC-20, SA-9, CA-3).
edge: ← refines from ARCH-FIGMA-AUTH
edge: ← refines from ARCH-FIGMA-EGRESS
edge: ← refines from SPIKE-FIGMA-FEASIBILITY
edge: ← satisfies from CAP-SEED-ATTACH-FIGMA
in_scope_of_contract: ReqALM product (build)
edge: → conforms_to to AC-20 (pin imprint=nist-800-53@rev5-dogfood-20261006)
edge: → conforms_to to SA-9 (pin imprint=nist-800-53@rev5-dogfood-20261006)
edge: → conforms_to to CA-3 (pin imprint=nist-800-53@rev5-dogfood-20261006)
edge: → conforms_to to SI-10 (pin imprint=nist-800-53@rev5-dogfood-20261006)
edge: → conforms_to to V-222606 (pin imprint=asd-stig@v6r4)
edge: → conforms_to to V-222428 (pin imprint=asd-stig@v6r4)
<<<
RELATIONS:
- TYPE: Parent
  VALUE: SEC-IO
- TYPE: Parent
  VALUE: ARCH-TRACE-RECHECK
  ROLE: Uses
- TYPE: Parent
  VALUE: ARCH-ATTACH-SERVE
  ROLE: Uses
- TYPE: Parent
  VALUE: AC-20
  ROLE: ConformsTo
- TYPE: Parent
  VALUE: SA-9
  ROLE: ConformsTo
- TYPE: Parent
  VALUE: CA-3
  ROLE: ConformsTo
- TYPE: Parent
  VALUE: SI-10
  ROLE: ConformsTo
- TYPE: Parent
  VALUE: V-222606
  ROLE: ConformsTo
- TYPE: Parent
  VALUE: V-222428
  ROLE: ConformsTo
- TYPE: Child
  VALUE: CONTRACT-ctr-reqalm-product
  ROLE: InScopeOf

[[SECTION]]
UID: ARCH-FIGMA-CHILDREN
TITLE: Children of ARCH-FIGMA

[REQUIREMENT]
UID: ARCH-FIGMA-AUTH
STATUS: Draft
TITLE: Figma outbound OAuth: PKCE, least scope, encrypted tokens
STATEMENT: >>>
Each project connects to Figma separately, which requires figma:connection:admin (Project admin) and step-up re-authentication, and is audited. The connection uses OAuth 2.0 authorization code with PKCE (S256) and the minimum read-only scopes needed (file content read, plus webhooks only if enabled). Access and refresh tokens are encrypted at rest under the KeyProvider (ARCH-KEY-SCOPE.1), refresh tokens are rotated on use, and a connection is revoked by setting revoked_at and calling the provider's revocation endpoint where supported. Tokens are never logged, never returned to the browser or MCP clients, and never placed in URLs. Outbound HTTP is restricted to an allowlist (api.figma.com, www.figma.com for the OAuth endpoints) over TLS with certificate validation.
<<<
COMMENT: >>>
KIND: requirement
BASE_UID: ARCH-FIGMA-AUTH
VERSION_N: 0
rbac_op: figma:connection:admin
priority: 30
iteration: iter-r2
security.catalog_ref: IA-5
security.verification_note: Cyber 2026-10-09 attachments-figma mapping; Draft, needs-spike. Outbound credentials join ARCH-KEY-SCOPE item (2).
in_scope_of_contract: ReqALM product (build)
edge: → conforms_to to IA-5 (pin imprint=nist-800-53@rev5-dogfood-20261006)
edge: → conforms_to to SC-28 (pin imprint=nist-800-53@rev5-dogfood-20261006)
edge: → conforms_to to SC-7 (pin imprint=nist-800-53@rev5-dogfood-20261006)
edge: → conforms_to to SC-8 (pin imprint=nist-800-53@rev5-dogfood-20261006)
edge: → conforms_to to V-222588 (pin imprint=asd-stig@v6r4)
edge: → conforms_to to V-222596 (pin imprint=asd-stig@v6r4)
<<<
RELATIONS:
- TYPE: Parent
  VALUE: ARCH-FIGMA
- TYPE: Parent
  VALUE: ARCH-FIGMA
  ROLE: Refines
- TYPE: Parent
  VALUE: ARCH-KEY-SCOPE.1
  ROLE: Refines
- TYPE: Parent
  VALUE: ARCH-KEY-PROVIDER
  ROLE: Uses
- TYPE: Parent
  VALUE: ARCH-CRED-REAUTH
  ROLE: Uses
- TYPE: Parent
  VALUE: IA-5
  ROLE: ConformsTo
- TYPE: Parent
  VALUE: SC-28
  ROLE: ConformsTo
- TYPE: Parent
  VALUE: SC-7
  ROLE: ConformsTo
- TYPE: Parent
  VALUE: SC-8
  ROLE: ConformsTo
- TYPE: Parent
  VALUE: V-222588
  ROLE: ConformsTo
- TYPE: Parent
  VALUE: V-222596
  ROLE: ConformsTo
- TYPE: Child
  VALUE: CONTRACT-ctr-reqalm-product
  ROLE: InScopeOf

[REQUIREMENT]
UID: ARCH-FIGMA-EGRESS
STATUS: Draft
TITLE: Figma data egress: classification, explicit export, audit
STATEMENT: >>>
By default ReqALM sends Figma only the file keys and node ids needed to fetch previews. Pushing trace data into Figma (for example uids and titles on a frame) is an explicit export that requires figma:export on the project, sends only uid, title, and status of items the caller can read, and writes an audit row listing the exported uids and destination file key. Items or projects marked restricted are never exported, are not counted, and are not named in errors. Statements, attachments, evidence, audit data, and identities are never sent to Figma.
<<<
COMMENT: >>>
KIND: requirement
BASE_UID: ARCH-FIGMA-EGRESS
VERSION_N: 0
rbac_op: figma:export
priority: 30
iteration: iter-r2
security.catalog_ref: AC-4
security.verification_note: Cyber 2026-10-09 attachments-figma mapping; Draft, needs-spike. Information-flow control for data leaving ReqALM.
in_scope_of_contract: ReqALM product (build)
edge: → conforms_to to AC-4 (pin imprint=nist-800-53@rev5-dogfood-20261006)
edge: → conforms_to to AU-2 (pin imprint=nist-800-53@rev5-dogfood-20261006)
edge: → conforms_to to AC-21 (pin imprint=nist-800-53@rev5-dogfood-20261006)
edge: → conforms_to to V-222428 (pin imprint=asd-stig@v6r4)
edge: → conforms_to to V-222427 (pin imprint=asd-stig@v6r4)
<<<
RELATIONS:
- TYPE: Parent
  VALUE: ARCH-FIGMA
- TYPE: Parent
  VALUE: ARCH-FIGMA
  ROLE: Refines
- TYPE: Parent
  VALUE: ARCH-ATTACH-AUDIT
  ROLE: Uses
- TYPE: Parent
  VALUE: ARCH-SEC-REL-STUB
  ROLE: Uses
- TYPE: Parent
  VALUE: AC-4
  ROLE: ConformsTo
- TYPE: Parent
  VALUE: AU-2
  ROLE: ConformsTo
- TYPE: Parent
  VALUE: AC-21
  ROLE: ConformsTo
- TYPE: Parent
  VALUE: V-222428
  ROLE: ConformsTo
- TYPE: Parent
  VALUE: V-222427
  ROLE: ConformsTo
- TYPE: Child
  VALUE: CONTRACT-ctr-reqalm-product
  ROLE: InScopeOf

[REQUIREMENT]
UID: SPIKE-FIGMA-FEASIBILITY
STATUS: Draft
TITLE: Spike: Figma integration feasibility (go/no-go)
STATEMENT: >>>
Before any Figma capability is planned, a time-boxed spike assesses and documents: Figma REST API rate limits and plan tiers; scale (files, nodes, and previews per project and cache size); the auth model (OAuth 2.0 with PKCE, available read-only scopes, token lifetime and refresh, per-project versus per-user connection); preview feasibility (server-side image export of frames and components, formats, latency); webhook availability, plan requirements, and signature or passcode verification; cost; and data egress (exactly what ReqALM must send to Figma). The outcome is a recorded go or no-go decision. Go updates ARCH-FIGMA, ARCH-FIGMA-AUTH, and ARCH-FIGMA-EGRESS by successor and then allows an implementation capability; no-go withdraws them.
<<<
COMMENT: >>>
KIND: requirement
BASE_UID: SPIKE-FIGMA-FEASIBILITY
VERSION_N: 0
rbac_op: figma:link
priority: 30
iteration: iter-r2
security.catalog_ref: SA-9
security.verification_note: Cyber 2026-10-09 attachments-figma mapping; Spike modeled as a draft requirement (seed has no spike/task kind). Outcome refines or withdraws ARCH-FIGMA*.
in_scope_of_contract: ReqALM product (build)
edge: → conforms_to to SA-9 (pin imprint=nist-800-53@rev5-dogfood-20261006)
edge: → conforms_to to CA-3 (pin imprint=nist-800-53@rev5-dogfood-20261006)
edge: → conforms_to to RA-3 (pin imprint=nist-800-53@rev5-dogfood-20261006)
<<<
RELATIONS:
- TYPE: Parent
  VALUE: ARCH-FIGMA
- TYPE: Parent
  VALUE: ARCH-FIGMA
  ROLE: Refines
- TYPE: Parent
  VALUE: SA-9
  ROLE: ConformsTo
- TYPE: Parent
  VALUE: CA-3
  ROLE: ConformsTo
- TYPE: Parent
  VALUE: RA-3
  ROLE: ConformsTo
- TYPE: Child
  VALUE: CONTRACT-ctr-reqalm-product
  ROLE: InScopeOf

[[/SECTION]]

[[/SECTION]]

[[SECTION]]
UID: SEC-AUDIT
TITLE: Audit & Ops

[TEXT]
UID: SEC-AUDIT-INTRO
STATEMENT: >>>
Audit log viewing, OTEL sink configuration, and health/version checks for operators and auditors.
<<<

[REQUIREMENT]
UID: CAP-AUDIT
STATUS: Active
TITLE: Audit & OTEL pack
STATEMENT: >>>
Capability pack for entity/client audit log reads and OTEL export configuration used by auditors
and ops. Auditor role allows audit:client:read within granted clients; cross-client reads deny.
Ops configures sinks without granting domain write.
<<<
COMMENT: >>>
KIND: capability
BASE_UID: CAP-AUDIT
VERSION_N: 0
priority: 25
iteration: iter-r1
security.catalog_ref: AC-3
security.verification_note: AC-3 access enforcement; AU-2/3/12 where mutating.
edge: ← uses from CAP-AUTH-AUDIT
in_scope_of_contract: Security package
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-AUDIT
- TYPE: Parent
  VALUE: M01
  ROLE: Satisfies
- TYPE: Parent
  VALUE: M02
  ROLE: Satisfies
- TYPE: Parent
  VALUE: ARCH-OTEL
  ROLE: Satisfies
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-security-package
  ROLE: InScopeOf
- TYPE: Child
  VALUE: CONTRACT-ctr-reqalm-product
  ROLE: InScopeOf
- TYPE: Child
  VALUE: RELEASE-rel-r1-core-alm
  ROLE: Delivers

[REQUIREMENT]
UID: M01
STATUS: Active
TITLE: View audit log for an entity
STATEMENT: >>>
An Auditor or Project admin views the audit log for a specific entity (requirement version, grant,
contract, etc.). ReqAML returns structured events with actor, action, and timestamps.
<<<
COMMENT: >>>
KIND: requirement
BASE_UID: M01
VERSION_N: 0
rbac_op: audit:entity:read
priority: 30
iteration: iter-r1
security.catalog_ref: AU-2
security.verification_note: AU-2/3/6/12 event review.
edge: ← satisfies from CAP-AUDIT
in_scope_of_contract: Security package
in_scope_of_contract: ReqALM product (build)
delivered_by_release: R1-core-ALM
edge: → conforms_to to AU-2 (pin imprint=nist-800-53@rev5-dogfood-20261006)
edge: → conforms_to to AU-6 (pin imprint=nist-800-53@rev5-dogfood-20261006)
edge: → conforms_to to AU-3 (pin imprint=nist-800-53@rev5-dogfood-20261006)
edge: → conforms_to to AU-9 (pin imprint=nist-800-53@rev5-dogfood-20261006)
edge: → conforms_to to AU-12 (pin imprint=nist-800-53@rev5-dogfood-20261006)
<<<
RELATIONS:
- TYPE: Parent
  VALUE: SEC-AUDIT
- TYPE: Parent
  VALUE: AU-2
  ROLE: ConformsTo
- TYPE: Parent
  VALUE: AU-6
  ROLE: ConformsTo
- TYPE: Parent
  VALUE: AU-3
  ROLE: ConformsTo
- TYPE: Parent
  VALUE: AU-9
  ROLE: ConformsTo
- TYPE: Parent
  VALUE: AU-12
  ROLE: ConformsTo
- TYPE: Child
  VALUE: CONTRACT-contract-security-package
  ROLE: InScopeOf
- TYPE: Child
  VALUE: CONTRACT-ctr-reqalm-product
  ROLE: InScopeOf
- TYPE: Child
  VALUE: RELEASE-rel-r1-core-alm
  ROLE: Delivers

[REQUIREMENT]
UID: M02
STATUS: Active
TITLE: View audit log for a client
STATEMENT: >>>
An Auditor views audit events across a client (permission-gated). ReqAML never returns other clients'
events even for platform operators without explicit break-glass outside product.
<<<
COMMENT: >>>
KIND: requirement
BASE_UID: M02
VERSION_N: 0
rbac_op: audit:client:read
priority: 35
iteration: iter-r1
security.catalog_ref: AU-6
security.verification_note: AU-6 audit review; cross-client isolation.
edge: ← satisfies from CAP-AUDIT
edge: ← uses from FIX-ALLOW-AUDIT-CLIENT
edge: ← uses from FIX-DENY-AUDIT-CROSS-CLIENT
in_scope_of_contract: Security package
in_scope_of_contract: ReqALM product (build)
edge: → conforms_to to AU-9 (pin imprint=nist-800-53@rev5-dogfood-20261006)
edge: → conforms_to to AU-6 (pin imprint=nist-800-53@rev5-dogfood-20261006)
<<<
RELATIONS:
- TYPE: Parent
  VALUE: SEC-AUDIT
- TYPE: Parent
  VALUE: AU-9
  ROLE: ConformsTo
- TYPE: Parent
  VALUE: AU-6
  ROLE: ConformsTo
- TYPE: Child
  VALUE: CONTRACT-contract-security-package
  ROLE: InScopeOf
- TYPE: Child
  VALUE: CONTRACT-ctr-reqalm-product
  ROLE: InScopeOf

[REQUIREMENT]
UID: M03
STATUS: Active
TITLE: Configure OTEL / log sinks
STATEMENT: >>>
An operator configures OTEL/OTLP endpoints and log sinks. ReqAML stores sink configuration and
validates connectivity without exposing sink credentials in API responses.
<<<
COMMENT: >>>
KIND: requirement
BASE_UID: M03
VERSION_N: 0
rbac_op: ops:otel:configure
priority: 50
iteration: iter-r2
security.catalog_ref: AU-12
security.verification_note: AU-12 audit generation pipeline config.
edge: ← refines from ARCH-CRED-TOKENS
edge: ← uses from ARCH-KEY-SCOPE
edge: ← uses from ARCH-KEY-SCOPE.1
in_scope_of_contract: Security package
in_scope_of_contract: ReqALM product (build)
edge: → conforms_to to AU-12 (pin imprint=nist-800-53@rev5-dogfood-20261006)
<<<
RELATIONS:
- TYPE: Parent
  VALUE: SEC-AUDIT
- TYPE: Parent
  VALUE: ARCH-OTEL
  ROLE: Uses
- TYPE: Parent
  VALUE: AU-12
  ROLE: ConformsTo
- TYPE: Child
  VALUE: CONTRACT-contract-security-package
  ROLE: InScopeOf
- TYPE: Child
  VALUE: CONTRACT-ctr-reqalm-product
  ROLE: InScopeOf

[REQUIREMENT]
UID: M04
STATUS: Active
TITLE: Health check / read API version
STATEMENT: >>>
Any authenticated caller (or public probe per deploy policy) reads health and API version.
ReqAML returns readiness without leaking client data. Health is not a substitute for scoped resource
authorization.
<<<
COMMENT: >>>
KIND: requirement
BASE_UID: M04
VERSION_N: 0
rbac_op: ops:health
priority: 20
iteration: iter-r0
security.catalog_ref: AC-3
security.verification_note: AC-3 access enforcement; AU-2/3/12 where mutating.
edge: ← uses from ARCH-DEVENV-HEALTH
edge: ← uses from FIX-ALLOW-DEVENV-SMOKE
edge: ← uses from ARCH-KEY-FAILCLOSED
edge: ← uses from ARCH-DEPLOY-MINIMAL
edge: ← uses from ARCH-BUILD-FOUNDATION
edge: ← satisfies from CAP-HEALTH-LIVENESS
edge: ← satisfies from CAP-READY-PROBES
in_scope_of_contract: Platform baseline
in_scope_of_contract: ReqALM product (build)
delivered_by_release: PR #12 — devenv foundation
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-AUDIT
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-platform-baseline
  ROLE: InScopeOf
- TYPE: Child
  VALUE: CONTRACT-ctr-reqalm-product
  ROLE: InScopeOf
- TYPE: Child
  VALUE: RELEASE-rel-pr12-devenv-foundation
  ROLE: Delivers
- TYPE: Child
  VALUE: RELEASE-rel-r1-core-alm
  ROLE: Delivers

[REQUIREMENT]
UID: ARCH-CHANGESET
STATUS: Active
TITLE: Project-scoped change sets with nested per-object audit
STATEMENT: >>>
Mutating audit is nested under project-scoped change_set records. A change_set may be a leaf (single user save / transaction) or an optional SDLC parent session that nests leaf change sets. Default scope is project; any hierarchy scope is allowed when opening an SDLC parent. audit_events optionally reference change_set_id. Open / close / revert / apply operate at the leaf; SDLC parents open/close as sessions (M05–M07). Closed change sets are retained forever (ARCH-CHANGESET-RETAIN). Revert policy is stack-ordered (ARCH-CHANGESET-CONFLICT / M07): only the latest non-abandoned change set on the stack may be reverted; older whole sets require abandoning that set and everything after it. Field-level history undo is a future want (WANT-CHANGESET-FIELD-UNDO).
<<<
COMMENT: >>>
KIND: requirement
BASE_UID: ARCH-CHANGESET
VERSION_N: 0
rbac_op: changeset:architecture
priority: 20
iteration: iter-r1
security.catalog_ref: AU-2
security.verification_note: Hybrid audit via change sets; AU-2/3/12. Per-object history + change-set index.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-AUDIT
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: ARCH-CHANGESET-RBAC
STATUS: Active
TITLE: Change-set RBAC (permission-tree: SDLC parent vs leaf)
STATEMENT: >>>
Change-set RBAC follows permission-tree.html (preferred over flat matrix where they disagree): open leaf = Author, Developer, Tester, Release manager, Security, Catalog steward, Project admin, Client admin (not Reader/AO/Auditor). Open/close SDLC parent = Author, Security (security sessions), Project admin, Client admin (client scope) — Developer is leaf-only and cannot open SDLC parent. Revert/re-apply = Author (own objects+rights), Security (security objects), Project/Client admin — not Developer. Read history = all roles.
<<<
COMMENT: >>>
KIND: requirement
BASE_UID: ARCH-CHANGESET-RBAC
VERSION_N: 0
rbac_op: changeset:rbac
priority: 20
iteration: iter-r1
security.catalog_ref: AC-6
security.verification_note: AC-6 least privilege; Developer leaf-only per permission-tree (flat matrix SDLC W for Developer overridden).
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-AUDIT
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: M05
STATUS: Active
TITLE: Open / close leaf change set
STATEMENT: >>>
An authorized actor opens a leaf change_set (user save / transaction) and closes it when the mutation batch completes. Leaf open is broader than SDLC parent (see ARCH-CHANGESET-RBAC). Audit events for the batch reference change_set_id.
<<<
COMMENT: >>>
KIND: requirement
BASE_UID: M05
VERSION_N: 0
rbac_op: changeset:leaf:open_close
priority: 30
iteration: iter-r1
security.catalog_ref: AU-2
security.verification_note: AU-2/3/12 change-set leaf lifecycle.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-AUDIT
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: M06
STATUS: Active
TITLE: Open / close SDLC parent change-set session
STATEMENT: >>>
Author, Security (security sessions), Project admin, or Client admin (client scope) opens or closes an SDLC parent change_set session. Developer cannot open SDLC parent (permission-tree). Nested leaf change sets attach via parent_id.
<<<
COMMENT: >>>
KIND: requirement
BASE_UID: M06
VERSION_N: 0
rbac_op: changeset:sdlc:open_close
priority: 30
iteration: iter-r1
security.catalog_ref: AU-2
security.verification_note: AU-2/3/12 SDLC parent session; Developer denied.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-AUDIT
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: M07
STATUS: Active
TITLE: Revert / re-apply latest change set on stack (or abandon suffix)
STATEMENT: >>>
Author (own objects + rights), Security (security objects), or Project/Client admin reverts or re-applies a change_set within their rights. Developer cannot revert/re-apply (permission-tree). Change sets are retained forever (ARCH-CHANGESET-RETAIN). Revert applies ONLY to the latest non-abandoned change set on the project stack (ARCH-CHANGESET-CONFLICT / gate-revert-latest-only). Attempting to revert a non-latest set denies (FIX-DENY-REVERT-NON-LATEST) unless the actor abandons that set and everything after it. Re-apply targets a reverted tip still at the stack head. Field-level history undo is a future want (WANT-CHANGESET-FIELD-UNDO), not M07 scope.
<<<
COMMENT: >>>
KIND: requirement
BASE_UID: M07
VERSION_N: 0
rbac_op: changeset:revert_apply
priority: 30
iteration: iter-r1
security.catalog_ref: AU-2
security.verification_note: AU-2/3/12 revert/re-apply; latest-only; Developer denied; FIX-DENY-REVERT-NON-LATEST.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-AUDIT
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: ARCH-CHANGESET-RETAIN
STATUS: Active
TITLE: Change sets retained forever; revert latest on stack only
STATEMENT: >>>
Closed (and open) change sets are retained forever for audit — no TTL deletion in product policy. Status may move to reverted or abandoned; records are never deleted. Authorized roles (M07) may revert only the latest change set on the project stack (ARCH-CHANGESET-CONFLICT). Re-apply restores a previously reverted tip when still latest. Older whole-set undo is via abandon of that set and every later set — not selective mid-stack revert. Field-level history undo is deferred (WANT-CHANGESET-FIELD-UNDO).
<<<
COMMENT: >>>
KIND: requirement
BASE_UID: ARCH-CHANGESET-RETAIN
VERSION_N: 0
rbac_op: changeset:retain
priority: 20
iteration: iter-r1
security.catalog_ref: AU-2
security.verification_note: AU-2/3/12 workflow / approval audit.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-AUDIT
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: ARCH-CHANGESET-CONFLICT
STATUS: Active
TITLE: Stack revert policy: latest-only; abandon suffix for older whole sets
STATEMENT: >>>
LOCKED stack revert policy (Dan 2026-10-07): (1) Only the latest change set on the stack may be reverted (changeset:revert). Non-latest whole-set revert DENIES (gate-revert-latest-only / FIX-DENY-REVERT-NON-LATEST). (2) Never revert an entire older change set unless that set AND everything after it are abandoned (abandon-suffix / unwind from tip). Abandoned sets remain retained forever (ARCH-CHANGESET-RETAIN) with status=abandoned. (3) Later product want: undo individual item fields from history without reverting whole older change sets (WANT-CHANGESET-FIELD-UNDO) — not encoded as current behavior. Tip revert may still surface unmanageable conflicts with external side effects (shipped delivers, closed contracts); those deny with FIX-DENY-* when defined. Do not invent mid-stack whole-set revert.
<<<
COMMENT: >>>
KIND: requirement
BASE_UID: ARCH-CHANGESET-CONFLICT
VERSION_N: 0
rbac_op: changeset:conflict_engine
priority: 20
iteration: iter-r1
security.catalog_ref: AU-2
security.verification_note: AU-2/3/12 workflow / approval audit.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-AUDIT
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: WANT-CHANGESET-FIELD-UNDO
STATUS: Active
TITLE: Future: undo individual item fields from history (not whole older change sets)
STATEMENT: >>>
FUTURE WANT (not current product behavior): allow undoing individual item fields from per-object history without reverting an entire older change set. Must not enable mid-stack whole-set revert (ARCH-CHANGESET-CONFLICT remains: only latest whole set, or abandon suffix). Encode UX/engine details when prioritized; until then M07 stays latest-only / abandon-suffix.
<<<
COMMENT: >>>
KIND: requirement
BASE_UID: WANT-CHANGESET-FIELD-UNDO
VERSION_N: 0
rbac_op: changeset:field_undo
priority: 40
iteration: iter-r2
security.catalog_ref: AU-2
security.verification_note: AU-2/3/12 revert / change-set audit.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-AUDIT
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: CAP-HEALTH-LIVENESS
STATUS: Active
TITLE: /health liveness probe with version
STATEMENT: >>>
GET /health is liveness only: it returns 200 with status ok, the app version and mode whenever the process can serve HTTP, and never touches Postgres, OpenBao or client data. Acceptance: /health stays 200 while dependencies are down (OpenBao sealed, Postgres stopped) so orchestrators do not restart a healthy process for a dependency outage.
<<<
COMMENT: >>>
KIND: capability
BASE_UID: CAP-HEALTH-LIVENESS
VERSION_N: 0
priority: 10
iteration: iter-r0
security.catalog_ref: SI-4
security.verification_note: No client data in the probe (M04). Verified 2026-10-07: /health 200 throughout the OpenBao-sealed and Postgres-stopped fault tests.
in_scope_of_contract: ReqALM product (build)
delivered_by_release: PR #12 — devenv foundation
edge: → conforms_to to SI-4 (pin imprint=nist-800-53@rev5-dogfood-20261006)
<<<
RELATIONS:
- TYPE: Parent
  VALUE: SEC-AUDIT
- TYPE: Parent
  VALUE: M04
  ROLE: Satisfies
- TYPE: Parent
  VALUE: SI-4
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-READY-PROBES
STATUS: Active
TITLE: /ready live peripheral and per-role checks (cached, time-boxed)
STATEMENT: >>>
GET /ready live-probes Postgres (SELECT 1), pending migrations, OpenBao (initialized, unsealed, Transit encrypt/decrypt round-trip on reqaml-kek) and each enabled role, caching results for REQAML_READY_CACHE_MS (2 s) and bounding each probe by REQAML_READY_PROBE_TIMEOUT_MS (3 s). It returns 503 with the failing check named and recovers without a restart. Acceptance: sealing OpenBao gives 503 with openbao failing; stopping Postgres gives 503 with database failing; both return to 200 after recovery; the app container is not restarted.
<<<
COMMENT: >>>
KIND: capability
BASE_UID: CAP-READY-PROBES
VERSION_N: 0
priority: 10
iteration: iter-r0
security.catalog_ref: SI-4
security.verification_note: Readiness gates traffic on live dependencies (ARCH-DEVENV-HEALTH). Verified 2026-10-07: OpenBao seal → 503 openbao 'sealed', unseal → 200; Postgres stop → 503 database ECONNREFUSED, recovery → 200; app restart count 0; unit tests for cache, database (incl. hung-DB timeout), migrations, openbao, roles. Fail-closed for key operations is R1.
in_scope_of_contract: ReqALM product (build)
delivered_by_release: PR #12 — devenv foundation
edge: → conforms_to to SI-4 (pin imprint=nist-800-53@rev5-dogfood-20261006)
<<<
RELATIONS:
- TYPE: Parent
  VALUE: SEC-AUDIT
- TYPE: Parent
  VALUE: ARCH-DEVENV-HEALTH
  ROLE: Satisfies
- TYPE: Parent
  VALUE: M04
  ROLE: Satisfies
- TYPE: Parent
  VALUE: ARCH-KEY-FAILCLOSED
  ROLE: Satisfies
- TYPE: Parent
  VALUE: SI-4
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-AUTH-AUDIT
STATUS: Active
TITLE: Authentication audit events (append-only)
STATEMENT: >>>
Authentication events are appended to `auth_audit_events`: local login success/failure, lockout, MFA verify, token issue/refresh/reuse/revoke, DCR deny, and RBAC deny samples. Acceptance: auth-flow-smoke exercises login, refresh reuse, revoke, lockout, and RBAC deny paths.
<<<
COMMENT: >>>
KIND: capability
BASE_UID: CAP-AUTH-AUDIT
VERSION_N: 0
priority: 10
iteration: iter-r1
security.catalog_ref: AU-2
security.verification_note: AU-2 / AU-3 / AU-12. Verified: Local Docker 2026-10-07 on PR #13 follow-up (6a5f0db + verification fixes), fresh volumes: `pnpm devenv:init` idempotent (byte-identical rerun), `--rotate` issues new secrets (needs `down -v` for the Postgres volume), secrets files mode 600 and gitignored; `docker compose up --build -d --wait` with and without the hostports overlay (app 127.0.0.1:3000 only; peripherals unpublished without the overlay, loopback-only with it); /ready all green, restart count 0; `pnpm devenv:smoke` pass incl. auth-flow-smoke (server-side OAuth handoffs, PKCE S256, refresh rotation/reuse family revoke, RFC7009 refresh+access revoke, lockout + username normalize, Reader RBAC 403, wrong audience 401 at MCP, upstream connectors 401 unauthenticated, session cookie HttpOnly+SameSite=Lax, cookie mutation without CSRF 401, signout ends session, sam-security MFA login via `devenv:mfa`, TOTP replay rejected (and one wrong code does not lock the account), agent tokens default Reader / Author max / Developer+ refused, TTL <= 1h, agent token revoked 401), auth_audit_events incl. agent-attributed mutation, IP throttle 200 -> 401 after 20 failures, production refused dev accounts/keys, missing REQALM_ISSUER_URL and blanket trustProxy; headless Chrome first-login TOTP enrollment (jamie-ao) then MFA re-login; `@reqalm/app` test 30/30, typecheck pass; seed yaml_to_strictdoc --validate pass; auth_audit_events rows observed for login success/failure, lockout, token issue/refresh/reuse/revoke, DCR deny and RBAC deny.
in_scope_of_contract: ReqALM product (build)
delivered_by_release: R1 — foundation shell + internal auth
edge: → conforms_to to AU-2 (pin imprint=nist-800-53@rev5-dogfood-20261006)
<<<
RELATIONS:
- TYPE: Parent
  VALUE: SEC-AUDIT
- TYPE: Parent
  VALUE: ARCH-CRED-AUDIT
  ROLE: Satisfies
- TYPE: Parent
  VALUE: CAP-AUDIT
  ROLE: Uses
- TYPE: Parent
  VALUE: AU-2
  ROLE: ConformsTo
- TYPE: Child
  VALUE: CONTRACT-ctr-reqalm-product
  ROLE: InScopeOf
- TYPE: Child
  VALUE: RELEASE-rel-r1-foundation-shell-auth
  ROLE: Delivers

[[/SECTION]]

[[SECTION]]
UID: SEC-UI
TITLE: UI Architecture

[TEXT]
UID: SEC-UI-INTRO
STATEMENT: >>>
React UI ownership chain from App providers through routes, layout, pages, and views, plus chrome that does not write domain data.
<<<

[REQUIREMENT]
UID: N01
STATUS: Active
TITLE: Toggle mind-map vs tree vs document view
STATEMENT: >>>
A Reader toggles among mind-map, tree outline, and document views. The toggle is chrome-only and
does not write domain data; underlying queries still honor Scoped View and RBAC.
<<<
COMMENT: >>>
KIND: requirement
BASE_UID: N01
VERSION_N: 0
rbac_op: ui:view_mode
priority: 30
iteration: iter-r0
security.catalog_ref: AC-3
security.verification_note: AC-3 access enforcement; AU-2/3/12 where mutating.
in_scope_of_contract: Platform baseline
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-UI
- TYPE: Parent
  VALUE: C06
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-platform-baseline
  ROLE: InScopeOf
- TYPE: Child
  VALUE: CONTRACT-ctr-reqalm-product
  ROLE: InScopeOf
- TYPE: Child
  VALUE: RELEASE-rel-r1-core-alm
  ROLE: Delivers

[REQUIREMENT]
UID: N02
STATUS: Active
TITLE: Pin favorite contract / project
STATEMENT: >>>
A Reader pins a favorite contract or project for quick navigation. Pins are per-user preferences
stored server-side or in user settings without altering domain junctions.
<<<
COMMENT: >>>
KIND: requirement
BASE_UID: N02
VERSION_N: 0
rbac_op: ui:pin
priority: 50
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-UI
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: N03
STATUS: Active
TITLE: Use global search
STATEMENT: >>>
A Reader uses global search across titles and statements in the scoped client. Results deep-link to
lines/versions and never include hits from other clients. Search respects the same AC-3 scope bind as
tree reads.
<<<
COMMENT: >>>
KIND: requirement
BASE_UID: N03
VERSION_N: 0
rbac_op: ui:global_search
priority: 25
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-UI
- TYPE: Parent
  VALUE: C08
  ROLE: Uses
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf
- TYPE: Child
  VALUE: RELEASE-rel-r1-core-alm
  ROLE: Delivers

[REQUIREMENT]
UID: ARCH-UI
STATUS: Active
TITLE: App → Routes → Layout → Page → View
STATEMENT: >>>
UI stack is App (auth + ClientScope) → Routes + guards → Layout → Page → View → pure components,
with optional stores scoped by clientId. Pages own data fetching; views stay presentational where practical.
Route guards enforce AC-3 in the shell (ARCH-UI-GUARD) but server RBAC remains authoritative.
<<<
COMMENT: >>>
KIND: requirement
BASE_UID: ARCH-UI
VERSION_N: 0
priority: 20
iteration: iter-r0
security.catalog_ref: AC-3
security.verification_note: Architecture enforces AC-3 via adapters/guards/layers.
edge: ← uses from ARCH-DEPLOY-MINIMAL
edge: ← uses from ARCH-BUILD-FOUNDATION
edge: ← satisfies from CAP-UI-FRAME
edge: ← satisfies from CAP-BROWSE-UI-CP
edge: ← satisfies from CAP-BROWSE-UI-REQS
edge: ← satisfies from CAP-BROWSE-UI-RELEASES
edge: ← satisfies from CAP-BROWSE-UI-TREE
edge: ← satisfies from CAP-UI-KIT
edge: ← refines from ARCH-UI-KIT-SHARED
edge: ← satisfies from CAP-UI-FRAME.1
edge: ← satisfies from CAP-BROWSE-UI-RELATIONS
edge: ← satisfies from CAP-UI-HEADER-NAV
edge: ← satisfies from CAP-UI-FRAME.2
edge: ← satisfies from CAP-BROWSE-UI-CP.1
edge: ← satisfies from CAP-BROWSE-UI-REQS.1
edge: ← satisfies from CAP-BROWSE-UI-RELEASES.1
edge: ← satisfies from CAP-BROWSE-UI-TREE.1
edge: ← satisfies from CAP-BROWSE-UI-RELATIONS.1
edge: ← satisfies from CAP-UI-HEADER-NAV.1
edge: ← satisfies from CAP-UI-LAYOUT
in_scope_of_contract: Design-2026-10
in_scope_of_contract: Platform baseline
in_scope_of_contract: ReqALM product (build)
delivered_by_release: R0-sequences
edge: → uses to ARCH-UI-GUARD (RELATIONS TYPE: Child; Parent would cycle)
edge: → conforms_to to AC-3 (pin imprint=nist-800-53@rev5-dogfood-20261006)
<<<
RELATIONS:
- TYPE: Parent
  VALUE: SEC-UI
- TYPE: Parent
  VALUE: ARCH-CP-HIER
  ROLE: Uses
- TYPE: Parent
  VALUE: AC-3
  ROLE: ConformsTo
- TYPE: Child
  VALUE: ARCH-UI-GUARD
  ROLE: Uses
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r0-sequences
  ROLE: Delivers

[[SECTION]]
UID: ARCH-UI-CHILDREN
TITLE: Children of ARCH-UI

[REQUIREMENT]
UID: ARCH-UI-GUARD
STATUS: Active
TITLE: Route guards enforce session + scope
STATEMENT: >>>
Protected shell routes require a valid session and, for project pages, a server-bound Client Scoped View.
Guards redirect to sign-in or scope selection rather than rendering empty shells with client-side-only checks.
<<<
COMMENT: >>>
KIND: requirement
BASE_UID: ARCH-UI-GUARD
VERSION_N: 0
priority: 15
iteration: iter-r0
security.catalog_ref: AC-3
security.verification_note: Route guards are AC-3 enforcement in the UI shell.
edge: ← uses from ARCH-UI
edge: ← uses from ARCH-CRED-SESSION
edge: ← satisfies from CAP-UI-FRAME
edge: ← satisfies from CAP-BROWSE-UI-CP
edge: ← satisfies from CAP-BROWSE-UI-REQS
edge: ← satisfies from CAP-BROWSE-UI-RELEASES
edge: ← satisfies from CAP-BROWSE-UI-TREE
edge: ← satisfies from CAP-MFA-QR
edge: ← satisfies from CAP-UI-FRAME.1
edge: ← satisfies from CAP-BROWSE-UI-RELATIONS
edge: ← satisfies from CAP-UI-HEADER-NAV
edge: ← satisfies from CAP-UI-FRAME.2
edge: ← satisfies from CAP-BROWSE-UI-CP.1
edge: ← satisfies from CAP-BROWSE-UI-REQS.1
edge: ← satisfies from CAP-BROWSE-UI-RELEASES.1
edge: ← satisfies from CAP-BROWSE-UI-TREE.1
edge: ← satisfies from CAP-BROWSE-UI-RELATIONS.1
edge: ← satisfies from CAP-UI-HEADER-NAV.1
edge: ← satisfies from CAP-UI-LAYOUT
edge: ← satisfies from CAP-BROWSE-UI-CATALOGS
edge: ← satisfies from CAP-BROWSE-UI-CONTRACTS
in_scope_of_contract: Design-2026-10
in_scope_of_contract: Security package
in_scope_of_contract: ReqALM product (build)
delivered_by_release: R1 — foundation shell + internal auth
edge: → conforms_to to AC-3 (pin imprint=nist-800-53@rev5-dogfood-20261006)
<<<
RELATIONS:
- TYPE: Parent
  VALUE: ARCH-UI
- TYPE: Parent
  VALUE: AC-3
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r1-foundation-shell-auth
  ROLE: Delivers

[[/SECTION]]

[REQUIREMENT]
UID: ARCH-APPROVAL-VIEW
STATUS: Active
TITLE: Approval queue tree (unapproved primary; approved dimmed/collapsed)
STATEMENT: >>>
The approval UI is a filtered requirement tree keyed by LINE: unapproved lines (and their head versions) are the primary visible set; approved lines are dimmed and/or collapsed — same interaction pattern as other filtered trees (C07). Readers with access can browse; only actors matching RoleBinding approver slots mutate ApprovalRecords. Supports Approve (line + direct children) and Approve Tree (full descendants).
<<<
COMMENT: >>>
KIND: requirement
BASE_UID: ARCH-APPROVAL-VIEW
VERSION_N: 0
rbac_op: requirement:tree:filter:approval
priority: 25
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-UI
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: ARCH-WF-ADMIN
STATUS: Active
TITLE: Workflow profile admin UI (Client/Project admin configures gates, slots, hooks)
STATEMENT: >>>
Client admin configures default WorkflowProfile and default RoleBindings for the client. Project admin selects/overrides the project's WorkflowProfile, enables/disables optional gates, edits per-project RoleBindings (slots), and reviews ActionHooks. Authors cannot redefine approver slots. Admin UI exposes gates, slots, hooks, and planning_gate_actions without requiring code changes for ordinary commercial vs DoD differences.
<<<
COMMENT: >>>
KIND: requirement
BASE_UID: ARCH-WF-ADMIN
VERSION_N: 0
rbac_op: workflow:profile:admin
priority: 25
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-UI
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: UI-APPROVE-LINE
STATUS: Active
TITLE: Approve action: selected line + direct children
STATEMENT: >>>
Approval UI action Approve selects a line and applies ApprovalRecord writes to that line PLUS its direct children only (not deeper descendants). Batched in one change set. Actor must match RoleBinding for the gate slot. Pairs D12 / requirement:line:approve.
<<<
COMMENT: >>>
KIND: requirement
BASE_UID: UI-APPROVE-LINE
VERSION_N: 0
rbac_op: requirement:line:approve
priority: 20
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-UI
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: UI-APPROVE-TREE
STATUS: Active
TITLE: Approve Tree action: selected line + full descendants
STATEMENT: >>>
Approval UI action Approve Tree selects a line and applies ApprovalRecord writes to that line AND all descendants (full subtree). Batched in one change set. Actor must match RoleBinding. Pairs D13 / requirement:line:approve_tree.
<<<
COMMENT: >>>
KIND: requirement
BASE_UID: UI-APPROVE-TREE
VERSION_N: 0
rbac_op: requirement:line:approve_tree
priority: 20
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-UI
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: CAP-UI-FRAME
STATUS: Draft
TITLE: UI frame: app shell, layout, guarded routes
STATEMENT: >>>
The Web UI frame served by the web role: top navigation, client-scoped sidebar chrome, and route guards that send unauthenticated users to the internal-AS sign-in flow and keep `/app/*` behind a valid API-audience session via HttpOnly SameSite=Lax cookies (BFF) with CSRF on sign-out; API clients use bearer tokens. Sign-out revokes refresh tokens via RFC 7009. Acceptance: unauthenticated `/app` redirects to login; authenticated shell renders `/api/v1/me` grants.
<<<
COMMENT: >>>
KIND: capability
BASE_UID: CAP-UI-FRAME
VERSION_N: 0
priority: 10
iteration: iter-r1
security.catalog_ref: AC-3
security.verification_note: AC-3 guard enforcement. Verified: Local Docker 2026-10-07 on PR #13 follow-up (6a5f0db + verification fixes), fresh volumes: `pnpm devenv:init` idempotent (byte-identical rerun), `--rotate` issues new secrets (needs `down -v` for the Postgres volume), secrets files mode 600 and gitignored; `docker compose up --build -d --wait` with and without the hostports overlay (app 127.0.0.1:3000 only; peripherals unpublished without the overlay, loopback-only with it); /ready all green, restart count 0; `pnpm devenv:smoke` pass incl. auth-flow-smoke (server-side OAuth handoffs, PKCE S256, refresh rotation/reuse family revoke, RFC7009 refresh+access revoke, lockout + username normalize, Reader RBAC 403, wrong audience 401 at MCP, upstream connectors 401 unauthenticated, session cookie HttpOnly+SameSite=Lax, cookie mutation without CSRF 401, signout ends session, sam-security MFA login via `devenv:mfa`, TOTP replay rejected (and one wrong code does not lock the account), agent tokens default Reader / Author max / Developer+ refused, TTL <= 1h, agent token revoked 401), auth_audit_events incl. agent-attributed mutation, IP throttle 200 -> 401 after 20 failures, production refused dev accounts/keys, missing REQALM_ISSUER_URL and blanket trustProxy; headless Chrome first-login TOTP enrollment (jamie-ao) then MFA re-login; `@reqalm/app` test 30/30, typecheck pass; seed yaml_to_strictdoc --validate pass; headless Chrome: `/` and `/app` redirect to sign-in, dev account casey-reader reaches `/app` at localhost:3000 and 127.0.0.1:3000.
edge: ← refines from CAP-UI-FRAME.1
delivered_by_release: R1 — foundation shell + internal auth
edge: → conforms_to to AC-3 (pin imprint=nist-800-53@rev5-dogfood-20261006)
<<<
RELATIONS:
- TYPE: Parent
  VALUE: SEC-UI
- TYPE: Parent
  VALUE: ARCH-UI
  ROLE: Satisfies
- TYPE: Parent
  VALUE: ARCH-UI-GUARD
  ROLE: Satisfies
- TYPE: Parent
  VALUE: AC-3
  ROLE: ConformsTo
- TYPE: Child
  VALUE: RELEASE-rel-r1-foundation-shell-auth
  ROLE: Delivers

[REQUIREMENT]
UID: CAP-UI-FRAME.1
STATUS: Draft
TITLE: UI frame: app shell, layout, guarded routes
STATEMENT: >>>
Web UI frame: navigation, client-scoped sidebar chrome, and route guards for /app/* via BFF session cookies and CSRF on cookie mutations. Partial: shell and sign-in work; not every ARCH-UI surface is implemented.
<<<
COMMENT: >>>
KIND: capability
BASE_UID: CAP-UI-FRAME
VERSION_N: 1
priority: 10
iteration: iter-r1
security.catalog_ref: AC-3
security.verification_note: Partial pass on .1: shell + guards verified on PR #13; full UI catalog still planned. Verified: Local Docker 2026-10-07 on PR #13 follow-up (6a5f0db + verification fixes).
edge: ← refines from CAP-UI-FRAME.2
edge: → conforms_to to AC-3 (pin imprint=nist-800-53@rev5-dogfood-20261006)
<<<
RELATIONS:
- TYPE: Parent
  VALUE: SEC-UI
- TYPE: Parent
  VALUE: CAP-UI-FRAME
  ROLE: Refines
- TYPE: Parent
  VALUE: ARCH-UI
  ROLE: Satisfies
- TYPE: Parent
  VALUE: ARCH-UI-GUARD
  ROLE: Satisfies
- TYPE: Parent
  VALUE: AC-3
  ROLE: ConformsTo
- TYPE: Parent
  VALUE: CAP-SVC-OPERATION-EXECUTOR.1
  ROLE: Uses
- TYPE: Parent
  VALUE: CAP-AUTH-HARDEN.1
  ROLE: Uses

[REQUIREMENT]
UID: CAP-UI-FRAME.2
STATUS: Active
TITLE: UI frame: app shell, layout, guarded routes
STATEMENT: >>>
Web UI frame (shipped partial): internal-AS sign-in, HttpOnly session cookies, CSRF on cookie-mutating routes, and route guards that keep unauthenticated users off /app/*. Top header chrome only — no persistent sidebar rail (CAP-UI-HEADER-NAV). Implemented today: grant-scoped read-only browse for clients, projects, requirements (list, tree, detail, version history, relationships panel), and releases under the header. Not implemented in this frame: contract/version/trace/catalog/planning screens (see draft CAP-UI-VIEW-* and CAP-CONTRACT-UI.1 / CAP-VERSION-UI.1).
<<<
COMMENT: >>>
KIND: capability
BASE_UID: CAP-UI-FRAME
VERSION_N: 2
priority: 10
iteration: iter-r1
security.catalog_ref: AC-3
security.verification_note: Content mint .2: header-only built shell; no sidebar rail.
in_scope_of_contract: ReqALM product (build)
edge: → conforms_to to AC-3 (pin imprint=nist-800-53@rev5-dogfood-20261006)
<<<
RELATIONS:
- TYPE: Parent
  VALUE: SEC-UI
- TYPE: Parent
  VALUE: CAP-UI-FRAME.1
  ROLE: Refines
- TYPE: Parent
  VALUE: ARCH-UI
  ROLE: Satisfies
- TYPE: Parent
  VALUE: ARCH-UI-GUARD
  ROLE: Satisfies
- TYPE: Parent
  VALUE: AC-3
  ROLE: ConformsTo
- TYPE: Parent
  VALUE: CAP-SVC-OPERATION-EXECUTOR.1
  ROLE: Uses
- TYPE: Parent
  VALUE: CAP-AUTH-HARDEN.1
  ROLE: Uses
- TYPE: Child
  VALUE: CONTRACT-ctr-reqalm-product
  ROLE: InScopeOf

[REQUIREMENT]
UID: ARCH-TRACE-VIEW-RTM
STATUS: Active
TITLE: Two-column requirements ↔ capabilities view
STATEMENT: >>>
The product shall provide a two-column traceability view with system requirements on the left and capabilities on the right, joined by satisfies edges (and refines where shown). Selecting a row on either column shall highlight the active joined path on both columns.
<<<
COMMENT: >>>
KIND: requirement
BASE_UID: ARCH-TRACE-VIEW-RTM
VERSION_N: 0
priority: 15
iteration: iter-r1
security.catalog_ref: CM-2
security.verification_note: Groomed 2026-10-09; pre-write or UI track.
edge: ← satisfies from CAP-UI-VIEW-RTM
in_scope_of_contract: ReqALM product (build)
<<<
RELATIONS:
- TYPE: Parent
  VALUE: SEC-UI
- TYPE: Parent
  VALUE: E06
  ROLE: Refines
- TYPE: Parent
  VALUE: CAP-UI-KIT-TREE
  ROLE: Uses
- TYPE: Child
  VALUE: CONTRACT-ctr-reqalm-product
  ROLE: InScopeOf

[REQUIREMENT]
UID: ARCH-TRACE-VIEW-CCM
STATUS: Active
TITLE: Two-column controls ↔ capabilities view
STATEMENT: >>>
The product shall provide a two-column traceability view with catalog controls on the left and capabilities on the right, joined by conforms_to edges. Selecting a row on either column shall highlight the active joined path on both columns. Direct ConformsTo pins shall render as solid links; inherited or aggregated links shall render dashed. A control shall be treated as heavy when it has more than 25 direct capability links in the current project view; heavy controls shall collapse into bundles by default with an expand affordance.
<<<
COMMENT: >>>
KIND: requirement
BASE_UID: ARCH-TRACE-VIEW-CCM
VERSION_N: 0
priority: 15
iteration: iter-r1
security.catalog_ref: CM-2
security.verification_note: Groomed 2026-10-09; pre-write or UI track.
edge: ← satisfies from CAP-UI-VIEW-CCM
in_scope_of_contract: ReqALM product (build)
<<<
RELATIONS:
- TYPE: Parent
  VALUE: SEC-UI
- TYPE: Parent
  VALUE: E06
  ROLE: Refines
- TYPE: Parent
  VALUE: CAP-UI-KIT-TREE
  ROLE: Uses
- TYPE: Child
  VALUE: CONTRACT-ctr-reqalm-product
  ROLE: InScopeOf

[REQUIREMENT]
UID: ARCH-TRACE-LAYOUT-WORKER
STATUS: Active
TITLE: Off-main-thread trace layout engine
STATEMENT: >>>
Layout, link aggregation, and rollup math for trace views shall run behind one small TypeScript interface executed off the main thread (Web Worker). The default implementation shall be plain TypeScript. WebAssembly shall be adopted only when plain TypeScript layout exceeds 50 ms at P95 on a reference project size (full dogfood trace graph).
<<<
COMMENT: >>>
KIND: requirement
BASE_UID: ARCH-TRACE-LAYOUT-WORKER
VERSION_N: 0
priority: 15
iteration: iter-r1
security.catalog_ref: CM-2
security.verification_note: Groomed 2026-10-09; pre-write or UI track.
edge: ← satisfies from CAP-UI-VIEW-RTM
edge: ← satisfies from CAP-UI-VIEW-CCM
in_scope_of_contract: ReqALM product (build)
<<<
RELATIONS:
- TYPE: Parent
  VALUE: SEC-UI
- TYPE: Parent
  VALUE: E06
  ROLE: Refines
- TYPE: Child
  VALUE: CONTRACT-ctr-reqalm-product
  ROLE: InScopeOf

[REQUIREMENT]
UID: ARCH-UI-KIT-SHARED
STATUS: Active
TITLE: UI Kit shared components
STATEMENT: >>>
A UI Kit capability shall own shared presentation components (tree, header chrome, badges) as child capabilities (part-of under CAP-UI-KIT). Feature views shall use the shared tree via uses edges. Tree behavior shall meet WCAG 2.2 Level AA and keyboard navigation per the WAI-ARIA tree pattern. Paging label 'showing 100 of N' shall appear when a parent has more than 100 direct children. CAP-BROWSE-UI-TREE (shipped) embeds tree behavior inline today; a later refactor shall extract that implementation into CAP-UI-KIT-TREE without duplicating a11y requirements.
<<<
COMMENT: >>>
KIND: requirement
BASE_UID: ARCH-UI-KIT-SHARED
VERSION_N: 0
priority: 15
iteration: iter-r1
security.catalog_ref: CM-2
security.verification_note: Groomed 2026-10-09; pre-write or UI track.
edge: ← satisfies from CAP-UI-KIT
edge: ← satisfies from CAP-UI-KIT-TREE
edge: ← satisfies from CAP-UI-KIT-CHROME
in_scope_of_contract: ReqALM product (build)
<<<
RELATIONS:
- TYPE: Parent
  VALUE: SEC-UI
- TYPE: Parent
  VALUE: ARCH-UI
  ROLE: Refines
- TYPE: Child
  VALUE: CONTRACT-ctr-reqalm-product
  ROLE: InScopeOf

[REQUIREMENT]
UID: ARCH-BROWSE-ROADMAP
STATUS: Active
TITLE: Read-only browse priority order
STATEMENT: >>>
The product shall provide read-only views for catalogs/imprints/controls, planning objects (contracts, iterations, change sets), capability artifacts, workflow objects, people/access bindings, and audit events — API first then matching browse UI per tranche. Delivery order and release names are recorded on CAP-BROWSE-ROADMAP. Relationships browse UI remains parallel (rel-r1-browse-ui-relations); do not duplicate here.
<<<
COMMENT: >>>
KIND: requirement
BASE_UID: ARCH-BROWSE-ROADMAP
VERSION_N: 0
rbac_op: requirement:tree:read
priority: 15
iteration: iter-r1
security.catalog_ref: CM-2
security.verification_note: Groomed 2026-10-09; pre-write or UI track.
edge: ← satisfies from CAP-SEED-GROOMING
edge: ← satisfies from CAP-BROWSE-ROADMAP
edge: ← satisfies from CAP-READ-PLANNING
in_scope_of_contract: ReqALM product (build)
<<<
RELATIONS:
- TYPE: Parent
  VALUE: SEC-UI
- TYPE: Parent
  VALUE: H09
  ROLE: Refines
- TYPE: Child
  VALUE: CONTRACT-ctr-reqalm-product
  ROLE: InScopeOf

[REQUIREMENT]
UID: CAP-UI-KIT
STATUS: Draft
TITLE: UI Kit (shared chrome and tree)
STATEMENT: >>>
Shared UI components for ReqALM browse surfaces: header chrome (CAP-UI-KIT-CHROME), badges, and the lazy tree control (CAP-UI-KIT-TREE). Feature pages compose these widgets; layout regions are documented on CAP-UI-LAYOUT and per-view capabilities.
<<<
COMMENT: >>>
KIND: capability
BASE_UID: CAP-UI-KIT
VERSION_N: 0
priority: 10
iteration: iter-r1
security.catalog_ref: CM-2
security.verification_note: Planned; not shipped on main.
edge: ← uses from CAP-UI-VIEW-RTM
edge: ← uses from CAP-UI-VIEW-CRITERIA
edge: ← uses from CAP-UI-VIEW-CATALOG
edge: ← uses from CAP-UI-VIEW-CCM
edge: ← uses from CAP-UI-VIEW-CAP-DETAIL
edge: ← uses from CAP-UI-VIEW-CAP-FOCUS
edge: ← uses from CAP-UI-LAYOUT
in_scope_of_contract: ReqALM product (build)
<<<
RELATIONS:
- TYPE: Parent
  VALUE: SEC-UI
- TYPE: Parent
  VALUE: ARCH-UI-KIT-SHARED
  ROLE: Satisfies
- TYPE: Parent
  VALUE: ARCH-UI
  ROLE: Satisfies
- TYPE: Parent
  VALUE: C07
  ROLE: Satisfies
- TYPE: Child
  VALUE: CONTRACT-ctr-reqalm-product
  ROLE: InScopeOf

[[SECTION]]
UID: CAP-UI-KIT-CHILDREN
TITLE: Children of CAP-UI-KIT

[REQUIREMENT]
UID: CAP-UI-KIT-TREE
STATUS: Draft
TITLE: Shared lazy tree widget
STATEMENT: >>>
Lazy tree with expand/collapse, WCAG 2.2 AA keyboard navigation per WAI-ARIA tree pattern, and parent paging label 'showing 100 of N' when more than 100 direct children exist. Layout role: primary column on the tree route; selecting a requirement navigates to the requirement detail route (no split-pane detail on the tree URL). Shipped CAP-BROWSE-UI-TREE will be refactored to consume this widget later (see ARCH-UI-KIT-SHARED).
<<<
COMMENT: >>>
KIND: capability
BASE_UID: CAP-UI-KIT-TREE
VERSION_N: 0
priority: 12
iteration: iter-r1
security.catalog_ref: CM-2
security.verification_note: Planned; tree browse exists in CAP-BROWSE-UI-TREE without extracted kit.
edge: ← uses from ARCH-TRACE-VIEW-RTM
edge: ← uses from ARCH-TRACE-VIEW-CCM
edge: ← uses from CAP-BROWSE-UI-TREE
edge: ← uses from CAP-BROWSE-UI-TREE.1
in_scope_of_contract: ReqALM product (build)
<<<
RELATIONS:
- TYPE: Parent
  VALUE: CAP-UI-KIT
- TYPE: Parent
  VALUE: ARCH-UI-KIT-SHARED
  ROLE: Satisfies
- TYPE: Child
  VALUE: CONTRACT-ctr-reqalm-product
  ROLE: InScopeOf

[REQUIREMENT]
UID: CAP-UI-KIT-CHROME
STATUS: Draft
TITLE: Shared header and badges
STATEMENT: >>>
Shared header chrome fragments and status badges for browse and trace views (brand slot, breadcrumb slot, tab strip host, account avatar). Consumed by CAP-UI-HEADER-NAV and feature pages via CAP-UI-KIT; no sidebar rail and no domain logic.
<<<
COMMENT: >>>
KIND: capability
BASE_UID: CAP-UI-KIT-CHROME
VERSION_N: 0
priority: 12
iteration: iter-r1
security.catalog_ref: CM-2
security.verification_note: Planned; tree browse exists in CAP-BROWSE-UI-TREE without extracted kit.
edge: ← uses from CAP-UI-HEADER-NAV
edge: ← uses from CAP-UI-HEADER-NAV.1
in_scope_of_contract: ReqALM product (build)
<<<
RELATIONS:
- TYPE: Parent
  VALUE: CAP-UI-KIT
- TYPE: Parent
  VALUE: ARCH-UI-KIT-SHARED
  ROLE: Satisfies
- TYPE: Child
  VALUE: CONTRACT-ctr-reqalm-product
  ROLE: InScopeOf

[[SECTION]]
UID: CAP-UI-KIT-CHROME-CHILDREN
TITLE: Children of CAP-UI-KIT-CHROME

[REQUIREMENT]
UID: CAP-UI-HEADER-NAV
STATUS: Draft
TITLE: ReqALM header and project navigation
STATEMENT: >>>
ReqALM /app shell header aligned to product chrome: brand mark, client/project/page breadcrumb with safe text, project-scoped tabs (Requirements with list/tree toggle, Releases; coming-soon stubs for Traceability, Capabilities, Contracts, Audit), minimal Clients/Projects nav outside project context, user initials avatar and sign out. Accessible nav landmarks, aria-current on active items, aria-disabled on stub tabs, visible focus styles. No sidebar.
<<<
COMMENT: >>>
KIND: capability
BASE_UID: CAP-UI-HEADER-NAV
VERSION_N: 0
priority: 10
iteration: iter-r1
security.catalog_ref: CM-2
security.verification_note: Shipped with header/nav UI PR #37 (merge dd43cc1523544d0f6375a628bc9d7d45a31fa738).
edge: ← refines from CAP-UI-HEADER-NAV.1
edge: ← satisfies from CAP-BROWSE-UI-CATALOGS
edge: ← satisfies from CAP-BROWSE-UI-CONTRACTS
delivered_by_release: R1 — ReqALM header and project navigation
<<<
RELATIONS:
- TYPE: Parent
  VALUE: CAP-UI-KIT-CHROME
- TYPE: Parent
  VALUE: ARCH-UI
  ROLE: Satisfies
- TYPE: Parent
  VALUE: ARCH-UI-GUARD
  ROLE: Satisfies
- TYPE: Parent
  VALUE: CAP-BROWSE-UI-REQS
  ROLE: Satisfies
- TYPE: Parent
  VALUE: CAP-UI-KIT-CHROME
  ROLE: Uses
- TYPE: Child
  VALUE: RELEASE-rel-r1-ui-header-nav
  ROLE: Delivers

[REQUIREMENT]
UID: CAP-UI-HEADER-NAV.1
STATUS: Active
TITLE: ReqALM header and project navigation
STATEMENT: >>>
ReqALM /app shell header aligned to product chrome: brand mark, client/project/page breadcrumb with safe text, project-scoped tabs (Requirements with list/tree toggle, Releases; coming-soon stubs for Traceability, Capabilities, Contracts, Audit), minimal Clients/Projects nav outside project context, user initials avatar and sign out. Accessible nav landmarks, aria-current on active items, aria-disabled on stub tabs, visible focus styles. No sidebar. Layout: Fixed top header — brand (links home), breadcrumb (client/project/page), project tab strip with Requirements list|tree toggle and Releases, stub tabs for Traceability/Capabilities/Contracts/Audit, avatar menu with sign-out. No sidebar; main content begins below the header.
<<<
COMMENT: >>>
KIND: capability
BASE_UID: CAP-UI-HEADER-NAV
VERSION_N: 1
priority: 10
iteration: iter-r1
security.catalog_ref: CM-2
security.verification_note: Layout cross-ref 2026-10-10 seed; shipped PR #37.
edge: ← uses from CAP-UI-LAYOUT
in_scope_of_contract: ReqALM product (build)
<<<
RELATIONS:
- TYPE: Parent
  VALUE: CAP-UI-KIT-CHROME
- TYPE: Parent
  VALUE: CAP-UI-HEADER-NAV
  ROLE: Refines
- TYPE: Parent
  VALUE: ARCH-UI
  ROLE: Satisfies
- TYPE: Parent
  VALUE: ARCH-UI-GUARD
  ROLE: Satisfies
- TYPE: Parent
  VALUE: CAP-BROWSE-UI-REQS
  ROLE: Satisfies
- TYPE: Parent
  VALUE: CAP-UI-KIT-CHROME
  ROLE: Uses
- TYPE: Child
  VALUE: CONTRACT-ctr-reqalm-product
  ROLE: InScopeOf

[[/SECTION]]

[[/SECTION]]

[REQUIREMENT]
UID: CAP-UI-LAYOUT
STATUS: Active
TITLE: ReqALM application layout (regions and navigation)
STATEMENT: >>>
ReqALM /app layout (no persistent sidebar): a fixed header band (CAP-UI-HEADER-NAV) spans the viewport with brand, client/project/page breadcrumb, project tabs, and account menu; the remaining viewport is the main content region. Main patterns: (1) paged list with URL-driven filters and row links to detail; (2) list + detail split (tree or table beside a detail pane); (3) single-column detail with secondary panels (version history, relationships); (4) two- or three-column trace boards with cross-highlighted join paths; (5) catalog pickers with imprint/control columns. Navigation: header tabs switch major project modes (Requirements list/tree, Releases, future Traceability/Capabilities/Contracts/Audit stubs); breadcrumbs and in-content links drill to requirement, release, capability, contract, and catalog routes; client-scoped routes under /app/clients and /app/projects/:projectId/*. All feature views consume shared chrome via CAP-UI-KIT (header, badges, tree widget).
<<<
COMMENT: >>>
KIND: capability
BASE_UID: CAP-UI-LAYOUT
VERSION_N: 0
priority: 10
iteration: iter-r1
security.catalog_ref: CM-2
security.verification_note: Shipped with UI layout seed PR #42 (merge 4d82bf9ab35ed63db675de8b187952cf60a434e5).
in_scope_of_contract: ReqALM product (build)
delivered_by_release: R1 — UI layout capability statements (seed)
<<<
RELATIONS:
- TYPE: Parent
  VALUE: SEC-UI
- TYPE: Parent
  VALUE: ARCH-UI
  ROLE: Satisfies
- TYPE: Parent
  VALUE: ARCH-UI-GUARD
  ROLE: Satisfies
- TYPE: Parent
  VALUE: CAP-UI-HEADER-NAV.1
  ROLE: Uses
- TYPE: Parent
  VALUE: CAP-UI-KIT
  ROLE: Uses
- TYPE: Child
  VALUE: CONTRACT-ctr-reqalm-product
  ROLE: InScopeOf
- TYPE: Child
  VALUE: RELEASE-rel-r1-ui-layout-capabilities
  ROLE: Delivers

[REQUIREMENT]
UID: CAP-UI-VIEW-RTM
STATUS: Draft
TITLE: Requirements ↔ capabilities trace view (mock)
STATEMENT: >>>
Planned two-column trace view under the project header: left column lists system requirements (filterable, scrollable); right column lists capabilities; center join highlights satisfies (and shown refines) edges when a row is selected on either side. Header breadcrumb holds project context; a back link returns to Requirements list/tree. Uses shared header chrome and badges from CAP-UI-KIT.
<<<
COMMENT: >>>
KIND: capability
BASE_UID: CAP-UI-VIEW-RTM
VERSION_N: 0
priority: 12
iteration: iter-r1
security.catalog_ref: CM-2
security.verification_note: Mockup files (Grok Bot box): 01-two-column-overview-v2.png, 02-two-column-suspect-highlight-v2.png.
in_scope_of_contract: ReqALM product (build)
<<<
RELATIONS:
- TYPE: Parent
  VALUE: SEC-UI
- TYPE: Parent
  VALUE: ARCH-TRACE-VIEW-RTM
  ROLE: Satisfies
- TYPE: Parent
  VALUE: ARCH-TRACE-LAYOUT-WORKER
  ROLE: Satisfies
- TYPE: Parent
  VALUE: CAP-UI-KIT
  ROLE: Uses
- TYPE: Child
  VALUE: CONTRACT-ctr-reqalm-product
  ROLE: InScopeOf

[REQUIREMENT]
UID: CAP-UI-VIEW-CRITERIA
STATUS: Draft
TITLE: Requirement acceptance criteria view (mock)
STATEMENT: >>>
Planned requirement detail extension: below the statement, an Acceptance criteria region lists facet rows (shall statements) with satisfied / incomplete / needs re-check badges; each facet links to satisfying capabilities when present. Header breadcrumb includes requirement uid; tabs remain on Requirements. Rollup status surfaces on the parent requirement header per ARCH-REQ-AC-ROLLUP.
<<<
COMMENT: >>>
KIND: capability
BASE_UID: CAP-UI-VIEW-CRITERIA
VERSION_N: 0
priority: 12
iteration: iter-r1
security.catalog_ref: CM-2
security.verification_note: Mockup files (Grok Bot box): 04-criteria-v2.png, 05-criteria-suspect-why-v2.png.
in_scope_of_contract: ReqALM product (build)
<<<
RELATIONS:
- TYPE: Parent
  VALUE: SEC-UI
- TYPE: Parent
  VALUE: ARCH-REQ-AC-FACET
  ROLE: Satisfies
- TYPE: Parent
  VALUE: ARCH-REQ-AC-ROLLUP
  ROLE: Satisfies
- TYPE: Parent
  VALUE: CAP-UI-KIT
  ROLE: Uses
- TYPE: Child
  VALUE: CONTRACT-ctr-reqalm-product
  ROLE: InScopeOf

[REQUIREMENT]
UID: CAP-UI-VIEW-CATALOG
STATUS: Draft
TITLE: Catalog browse three-column view (mock)
STATEMENT: >>>
Planned catalog browse under Capabilities/Catalog tab: column one lists visible catalogs for the project (ARCH-CAT-VISIBILITY); column two lists imprints/versions for the selected catalog; column three lists controls with conforming counts. Row selection loads control detail in a slide-over or replaces column three. Links from control rows jump to catalog-to-capability trace (CAP-UI-VIEW-CCM) when trace is enabled.
<<<
COMMENT: >>>
KIND: capability
BASE_UID: CAP-UI-VIEW-CATALOG
VERSION_N: 0
priority: 12
iteration: iter-r1
security.catalog_ref: CM-2
security.verification_note: Mockup files (Grok Bot box): 06c-catalog-BC-three-column-v2.png, 06e-catalog-BC-three-column-AC3-v2.png.
in_scope_of_contract: ReqALM product (build)
<<<
RELATIONS:
- TYPE: Parent
  VALUE: SEC-UI
- TYPE: Parent
  VALUE: ARCH-CAT-VISIBILITY
  ROLE: Satisfies
- TYPE: Parent
  VALUE: ARCH-CAT-EXTERNAL
  ROLE: Satisfies
- TYPE: Parent
  VALUE: CAP-UI-KIT
  ROLE: Uses
- TYPE: Child
  VALUE: CONTRACT-ctr-reqalm-product
  ROLE: InScopeOf

[REQUIREMENT]
UID: CAP-UI-VIEW-CCM
STATUS: Draft
TITLE: Catalog ↔ capabilities trace view (mock)
STATEMENT: >>>
Planned two-column trace view: left column lists catalog controls (respecting visible catalog set); right column lists capabilities; joins follow conforms_to with solid direct pins and dashed inherited/heavy-bundle links per ARCH-TRACE-VIEW-CCM. Selection highlights paired rows; capability rows link to capability detail (CAP-UI-VIEW-CAP-DETAIL). Header shows catalog + project context.
<<<
COMMENT: >>>
KIND: capability
BASE_UID: CAP-UI-VIEW-CCM
VERSION_N: 0
priority: 12
iteration: iter-r1
security.catalog_ref: CM-2
security.verification_note: Mockup files (Grok Bot box): 07a-catalog-caps-collapsed-v2.png, 07b-catalog-caps-AC3-expanded-v2.png.
in_scope_of_contract: ReqALM product (build)
<<<
RELATIONS:
- TYPE: Parent
  VALUE: SEC-UI
- TYPE: Parent
  VALUE: ARCH-TRACE-VIEW-CCM
  ROLE: Satisfies
- TYPE: Parent
  VALUE: ARCH-TRACE-LAYOUT-WORKER
  ROLE: Satisfies
- TYPE: Parent
  VALUE: CAP-UI-KIT
  ROLE: Uses
- TYPE: Child
  VALUE: CONTRACT-ctr-reqalm-product
  ROLE: InScopeOf

[REQUIREMENT]
UID: CAP-UI-VIEW-CAP-DETAIL
STATUS: Draft
TITLE: Capability detail view (mock)
STATEMENT: >>>
Planned capability detail: header with uid, title, status, verification outcome; statement body; sections for part-of children, satisfies/requirements links, conforms_to control pins (with inherited-via-uses chips), artifacts/attachments list, and delivered-in releases. Relationships to catalog controls link to CAP-UI-VIEW-CCM; requirement peers open requirement detail. Uses CAP-UI-KIT header and badges.
<<<
COMMENT: >>>
KIND: capability
BASE_UID: CAP-UI-VIEW-CAP-DETAIL
VERSION_N: 0
priority: 12
iteration: iter-r1
security.catalog_ref: CM-2
security.verification_note: Mockup files (Grok Bot box): 09-capability-detail.png.
in_scope_of_contract: ReqALM product (build)
<<<
RELATIONS:
- TYPE: Parent
  VALUE: SEC-UI
- TYPE: Parent
  VALUE: I01
  ROLE: Satisfies
- TYPE: Parent
  VALUE: I03
  ROLE: Satisfies
- TYPE: Parent
  VALUE: ARCH-HIER-CAP-PARTOF
  ROLE: Satisfies
- TYPE: Parent
  VALUE: CAP-UI-KIT
  ROLE: Uses
- TYPE: Child
  VALUE: CONTRACT-ctr-reqalm-product
  ROLE: InScopeOf

[REQUIREMENT]
UID: CAP-UI-VIEW-CAP-FOCUS
STATUS: Draft
TITLE: Capability and release focus view (mock)
STATEMENT: >>>
Planned focus screen for a capability line within a release or iteration context: top summary shows capability uid/title, verification badge, and part-of parent; a Releases strip lists planned/shipped releases that deliver this capability with links to release detail; main body lists child capabilities (part-of) and satisfies targets. Breadcrumb: project → Capabilities → uid. Links to requirement/detail routes for satisfied requirements.
<<<
COMMENT: >>>
KIND: capability
BASE_UID: CAP-UI-VIEW-CAP-FOCUS
VERSION_N: 0
priority: 12
iteration: iter-r1
security.catalog_ref: CM-2
security.verification_note: Mockup files (Grok Bot box): 10a-focus-cap-rbac.png, 10d-focus-picker-search.png, 11a-focus-release-r1-foundation-shipped.png.
in_scope_of_contract: ReqALM product (build)
<<<
RELATIONS:
- TYPE: Parent
  VALUE: SEC-UI
- TYPE: Parent
  VALUE: ARCH-HIER-CAP-PARTOF
  ROLE: Satisfies
- TYPE: Parent
  VALUE: ARCH-RELEASE
  ROLE: Satisfies
- TYPE: Parent
  VALUE: CAP-UI-KIT
  ROLE: Uses
- TYPE: Child
  VALUE: CONTRACT-ctr-reqalm-product
  ROLE: InScopeOf

[[/SECTION]]

[[SECTION]]
UID: SEC-API
TITLE: API Architecture

[TEXT]
UID: SEC-API-INTRO
STATEMENT: >>>
Node API layers HTTP adapters, RBAC, business services, audit, and schema-first data providers against Postgres.
<<<

[REQUIREMENT]
UID: ARCH-OTEL
STATUS: Active
TITLE: OTEL audit trail
STATEMENT: >>>
Security-relevant actions emit structured audit events exported via OTEL (OTLP) for centralized
review, aligned to NIST AU-2/3/6/9/12. Session teardown destroys session identifiers (V-222578).
Auditors read via M01/M02; actors cannot alter prior audit rows (AU-9).
<<<
COMMENT: >>>
KIND: requirement
BASE_UID: ARCH-OTEL
VERSION_N: 0
priority: 25
iteration: iter-r0
security.catalog_ref: AU-2
security.verification_note: AU-2/3/6/12. ASD STIG V6R4 V-222578 (session ID destroy complements audit lifecycle).
edge: ← satisfies from CAP-AUDIT
edge: ← uses from M03
edge: ← refines from ARCH-CRED-AUDIT
edge: ← uses from ARCH-KEY-LIFECYCLE
edge: ← uses from ARCH-BUILD-FOUNDATION
edge: ← uses from ARCH-AUTH-AGENT-ATTRIBUTION
edge: ← uses from ARCH-OTEL-TRACE
edge: ← refines from ARCH-WRITE-UOW-AUDIT
edge: ← refines from ARCH-WRITE-AUDIT-FLOOD
in_scope_of_contract: Design-2026-10
in_scope_of_contract: Security package
in_scope_of_contract: ReqALM product (build)
delivered_by_release: R0-sequences
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
edge: → conforms_to to V-222578 (pin imprint=asd-stig@v6r4)
edge: → conforms_to to AU-6 (pin imprint=nist-800-53@rev5-dogfood-20261006)
<<<
RELATIONS:
- TYPE: Parent
  VALUE: SEC-API
- TYPE: Parent
  VALUE: AU-2
  ROLE: ConformsTo
- TYPE: Parent
  VALUE: A01
  ROLE: Refines
- TYPE: Parent
  VALUE: G05
  ROLE: Refines
- TYPE: Parent
  VALUE: AU-3
  ROLE: ConformsTo
- TYPE: Parent
  VALUE: AU-12
  ROLE: ConformsTo
- TYPE: Parent
  VALUE: V-222578
  ROLE: ConformsTo
- TYPE: Parent
  VALUE: AU-6
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r0-sequences
  ROLE: Delivers

[REQUIREMENT]
UID: ARCH-API
STATUS: Active
TITLE: HTTP → business → data, OpenAPI schema-first
STATEMENT: >>>
API is schema-first (Zod + OpenAPI): HTTP adapters validate DTOs, RBAC authorizes, business services
orchestrate, data providers implement repositories against Postgres. Invalid input never reaches domain
mutations (SI-10). The same stack serves UI and MCP tools.
<<<
COMMENT: >>>
KIND: requirement
BASE_UID: ARCH-API
VERSION_N: 0
priority: 20
iteration: iter-r0
security.catalog_ref: AC-3
security.verification_note: Architecture enforces AC-3 via adapters/guards/layers.
edge: ← uses from MC02
edge: ← uses from ARCH-AUTH-AS
edge: ← uses from ARCH-DEPLOY-MINIMAL
edge: ← uses from ARCH-BUILD-FOUNDATION
edge: ← satisfies from CAP-API-DOCS-SEED-SUMMARY
edge: ← satisfies from CAP-SVC-RESULT-ENVELOPE
edge: ← refines from ARCH-SEC-REL-PAGING
edge: ← refines from ARCH-SEC-HEADERS
in_scope_of_contract: Design-2026-10
in_scope_of_contract: Platform baseline
in_scope_of_contract: ReqALM product (build)
delivered_by_release: R0-sequences
edge: → uses to ARCH-API-RBAC (RELATIONS TYPE: Child; Parent would cycle)
edge: → uses to ARCH-API-LAYERS (RELATIONS TYPE: Child; Parent would cycle)
edge: → conforms_to to SI-10 (pin imprint=nist-800-53@rev5-dogfood-20261006)
edge: → conforms_to to AC-3 (pin imprint=nist-800-53@rev5-dogfood-20261006)
<<<
RELATIONS:
- TYPE: Parent
  VALUE: SEC-API
- TYPE: Parent
  VALUE: ARCH-VER
  ROLE: Uses
- TYPE: Parent
  VALUE: SI-10
  ROLE: ConformsTo
- TYPE: Parent
  VALUE: AC-3
  ROLE: ConformsTo
- TYPE: Child
  VALUE: ARCH-API-RBAC
  ROLE: Uses
- TYPE: Child
  VALUE: ARCH-API-LAYERS
  ROLE: Uses
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r0-sequences
  ROLE: Delivers

[[SECTION]]
UID: ARCH-API-CHILDREN
TITLE: Children of ARCH-API

[REQUIREMENT]
UID: ARCH-API-RBAC
STATUS: Draft
TITLE: RBAC on every mutating API
STATEMENT: >>>
Every mutating business operation checks project_grant (and steward grants where applicable) before
writes. Denied calls return a consistent unauthorized/forbidden outcome and emit an audit event.
<<<
COMMENT: >>>
KIND: requirement
BASE_UID: ARCH-API-RBAC
VERSION_N: 0
rbac_op: rbac:authorize
priority: 10
iteration: iter-r0
security.catalog_ref: REQALM-SEC-RBAC
security.verification_note: Maps to ReqALM RBAC catalog item.
edge: ← uses from ARCH-API
edge: ← satisfies from CAP-RBAC
edge: ← uses from ARCH-AUTH-AUDIENCE
edge: ← uses from ARCH-KEY-CUSTODIAN
edge: ← uses from ARCH-BUILD-FOUNDATION
edge: ← uses from ARCH-AUTH-CLAIM-MAP
edge: ← satisfies from CAP-SVC-REQUEST-CONTEXT
edge: ← satisfies from CAP-SVC-OPERATION-EXECUTOR
edge: ← satisfies from CAP-SVC-ROUTE-REGISTRY
edge: ← satisfies from CAP-SVC-PROJECT-READ
edge: ← satisfies from CAP-SVC-OPERATION-ROUTE
edge: ← satisfies from CAP-SVC-BUSINESS-ROUTE-AUDIT
edge: ← satisfies from CAP-SVC-PROJECT-ID-SLUG
edge: ← satisfies from CAP-SVC-IMPLICIT-PUBLIC-EXACT
edge: ← satisfies from CAP-SVC-NON-API-AUTH-AUDIT
edge: ← satisfies from CAP-READ-REQS
edge: ← satisfies from CAP-READ-RELEASES
edge: ← satisfies from CAP-READ-HIERARCHY
edge: ← satisfies from CAP-RELATIONS-API
edge: ← refines from ARCH-API-RBAC.1
edge: ← satisfies from CAP-CATALOGS-API
edge: ← satisfies from CAP-SVC-OPERATION-EXECUTOR.1
edge: ← satisfies from CAP-SVC-RBAC-NO-PROJECT
edge: ← satisfies from CAP-SVC-HARDENING-FOLLOWUP
in_scope_of_contract: Design-2026-10
in_scope_of_contract: Security package
delivered_by_release: R1 — foundation shell + internal auth
edge: → conforms_to to AC-3 (pin imprint=nist-800-53@rev5-dogfood-20261006)
edge: → conforms_to to AC-2 (pin imprint=nist-800-53@rev5-dogfood-20261006)
edge: → conforms_to to AC-6 (pin imprint=nist-800-53@rev5-dogfood-20261006)
edge: → conforms_to to V-222429 (pin imprint=asd-stig@v6r4)
<<<
RELATIONS:
- TYPE: Parent
  VALUE: ARCH-API
- TYPE: Parent
  VALUE: AC-3
  ROLE: ConformsTo
- TYPE: Parent
  VALUE: AC-2
  ROLE: ConformsTo
- TYPE: Parent
  VALUE: AC-6
  ROLE: ConformsTo
- TYPE: Parent
  VALUE: V-222429
  ROLE: ConformsTo
- TYPE: Child
  VALUE: CONTRACT-contract-design-2026-10
  ROLE: InScopeOf
- TYPE: Child
  VALUE: CONTRACT-contract-security-package
  ROLE: InScopeOf
- TYPE: Child
  VALUE: RELEASE-rel-r1-foundation-shell-auth
  ROLE: Delivers

[REQUIREMENT]
UID: ARCH-API-RBAC.1
STATUS: Active
TITLE: RBAC on every mutating API
STATEMENT: >>>
Every mutating business operation shall check project_grant (and steward grants where applicable) before writes. Denied calls return a consistent unauthorized/forbidden outcome and emit an audit event. CAP-RBAC documents the currently verified enforcement subset; this architecture requirement remains active until all mutators in scope ship.
<<<
COMMENT: >>>
KIND: requirement
BASE_UID: ARCH-API-RBAC
VERSION_N: 1
rbac_op: rbac:authorize
priority: 10
iteration: iter-r0
security.catalog_ref: REQALM-SEC-RBAC
security.verification_note: Maps to ReqALM RBAC catalog item; .1 narrows honesty vs CAP-RBAC enforcement subset.
edge: ← refines from ARCH-SEC-XPROJ-READ
edge: ← satisfies from CAP-RBAC.1
edge: ← uses from ARCH-ATTACH-SCOPE.1
edge: ← uses from ARCH-ATTACH-SCOPE
edge: ← uses from ARCH-ATTACH-UPLOAD
in_scope_of_contract: ReqALM product (build)
edge: → conforms_to to AC-3 (pin imprint=nist-800-53@rev5-dogfood-20261006)
edge: → conforms_to to AC-2 (pin imprint=nist-800-53@rev5-dogfood-20261006)
edge: → conforms_to to AC-6 (pin imprint=nist-800-53@rev5-dogfood-20261006)
edge: → conforms_to to V-222429 (pin imprint=asd-stig@v6r4)
<<<
RELATIONS:
- TYPE: Parent
  VALUE: ARCH-API
- TYPE: Parent
  VALUE: ARCH-API-RBAC
  ROLE: Refines
- TYPE: Parent
  VALUE: AC-3
  ROLE: ConformsTo
- TYPE: Parent
  VALUE: AC-2
  ROLE: ConformsTo
- TYPE: Parent
  VALUE: AC-6
  ROLE: ConformsTo
- TYPE: Parent
  VALUE: V-222429
  ROLE: ConformsTo
- TYPE: Child
  VALUE: CONTRACT-ctr-reqalm-product
  ROLE: InScopeOf

[REQUIREMENT]
UID: ARCH-API-LAYERS
STATUS: Active
TITLE: Layering: adapter → service → repository
STATEMENT: >>>
HTTP adapters do not embed SQL. Business services own orchestration and authorization calls; repositories
own persistence. This layering is mandatory for MCP tools and UI clients alike and keeps AC-3 checks in
one place (ARCH-API-RBAC).
<<<
COMMENT: >>>
KIND: requirement
BASE_UID: ARCH-API-LAYERS
VERSION_N: 0
priority: 20
iteration: iter-r0
security.catalog_ref: AC-3
security.verification_note: Architecture enforces AC-3 via adapters/guards/layers.
edge: ← uses from ARCH-API
edge: ← satisfies from CAP-SVC-RESULT-ENVELOPE
edge: ← satisfies from CAP-SVC-REQUEST-CONTEXT
edge: ← satisfies from CAP-SVC-MODULE-BOOTSTRAP
edge: ← satisfies from CAP-SVC-OPERATION-ROUTE
edge: ← refines from ARCH-WRITE-REPOSITORY-LAYER
in_scope_of_contract: Design-2026-10
in_scope_of_contract: Platform baseline
in_scope_of_contract: ReqALM product (build)
delivered_by_release: R1 platform follow-ups (deferred from foundation PR)
edge: → conforms_to to AC-3 (pin imprint=nist-800-53@rev5-dogfood-20261006)
<<<
RELATIONS:
- TYPE: Parent
  VALUE: ARCH-API
- TYPE: Parent
  VALUE: AC-3
  ROLE: ConformsTo
- TYPE: Child
  VALUE: CONTRACT-contract-design-2026-10
  ROLE: InScopeOf
- TYPE: Child
  VALUE: CONTRACT-contract-platform-baseline
  ROLE: InScopeOf
- TYPE: Child
  VALUE: CONTRACT-ctr-reqalm-product
  ROLE: InScopeOf
- TYPE: Child
  VALUE: RELEASE-rel-r1-platform-followups
  ROLE: Delivers

[[/SECTION]]

[REQUIREMENT]
UID: CAP-API-DOCS-SEED-SUMMARY
STATUS: Active
TITLE: OpenAPI docs (/docs) and seed summary endpoint
STATEMENT: >>>
The API role serves its static OpenAPI 3.1 spec (apps/reqaml/openapi/openapi.yaml) through Swagger UI at /docs (JSON at /docs/json) and exposes GET /api/v1/seed/summary with aggregate seed counts (identities, grants, requirement lines and versions, capabilities, releases) and a sample identity, without client content. Acceptance: /docs and /docs/json return 200; the summary reflects the loaded dogfood seed and is unchanged after a seed re-run.
<<<
COMMENT: >>>
KIND: capability
BASE_UID: CAP-API-DOCS-SEED-SUMMARY
VERSION_N: 0
priority: 10
iteration: iter-r0
security.catalog_ref: SA-5
security.verification_note: SA-5 system documentation served from the schema-first spec. Verified 2026-10-07: /docs 200, /docs/json 200, /api/v1/seed/summary 200 with seed counts (smoke asserts it).
in_scope_of_contract: ReqALM product (build)
delivered_by_release: PR #12 — devenv foundation
edge: → conforms_to to SA-5 (pin imprint=nist-800-53@rev5-dogfood-20261006)
<<<
RELATIONS:
- TYPE: Parent
  VALUE: SEC-API
- TYPE: Parent
  VALUE: ARCH-API
  ROLE: Satisfies
- TYPE: Parent
  VALUE: ARCH-DEVENV-CLONE
  ROLE: Satisfies
- TYPE: Parent
  VALUE: SA-5
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-SVC-RESULT-ENVELOPE
STATUS: Active
TITLE: ServiceResult + HTTP Problem Details envelope
STATEMENT: >>>
Typed ServiceResult (ok/err codes) and mapServiceResultToHttp for data and errors with request_id.
<<<
COMMENT: >>>
KIND: capability
BASE_UID: CAP-SVC-RESULT-ENVELOPE
VERSION_N: 0
priority: 10
iteration: iter-r1
security.catalog_ref: CM-2
security.verification_note: Planned until service-foundation PR merges.
edge: ← satisfies from CAP-SVC-PROBLEM-JSON
in_scope_of_contract: ReqALM product (build)
delivered_by_release: R1 — API service foundation (context, RBAC ops, audit, envelope)
<<<
RELATIONS:
- TYPE: Parent
  VALUE: SEC-API
- TYPE: Parent
  VALUE: ARCH-API
  ROLE: Satisfies
- TYPE: Parent
  VALUE: ARCH-API-LAYERS
  ROLE: Satisfies
- TYPE: Child
  VALUE: CONTRACT-ctr-reqalm-product
  ROLE: InScopeOf
- TYPE: Child
  VALUE: RELEASE-rel-r1-service-foundation
  ROLE: Delivers

[REQUIREMENT]
UID: CAP-SVC-REQUEST-CONTEXT
STATUS: Active
TITLE: Per-request RequestContext for services
STATEMENT: >>>
buildRequestContext supplies identity, grants, roles, agent attribution, logger, pool, and request id.
<<<
COMMENT: >>>
KIND: capability
BASE_UID: CAP-SVC-REQUEST-CONTEXT
VERSION_N: 0
priority: 10
iteration: iter-r1
security.catalog_ref: CM-2
security.verification_note: Planned until service-foundation PR merges.
in_scope_of_contract: ReqALM product (build)
delivered_by_release: R1 — API service foundation (context, RBAC ops, audit, envelope)
<<<
RELATIONS:
- TYPE: Parent
  VALUE: SEC-API
- TYPE: Parent
  VALUE: ARCH-API-LAYERS
  ROLE: Satisfies
- TYPE: Parent
  VALUE: ARCH-API-RBAC
  ROLE: Satisfies
- TYPE: Child
  VALUE: CONTRACT-ctr-reqalm-product
  ROLE: InScopeOf
- TYPE: Child
  VALUE: RELEASE-rel-r1-service-foundation
  ROLE: Delivers

[REQUIREMENT]
UID: CAP-SVC-OPERATION-EXECUTOR
STATUS: Draft
TITLE: Operation executor (authorize → execute → audit → log)
STATEMENT: >>>
runOperation enforces RBAC + project scope, writes audit_events, structured logs, returns ServiceResult.
<<<
COMMENT: >>>
KIND: capability
BASE_UID: CAP-SVC-OPERATION-EXECUTOR
VERSION_N: 0
priority: 10
iteration: iter-r1
security.catalog_ref: CM-2
security.verification_note: Planned until service-foundation PR merges.
edge: ← refines from CAP-SVC-OPERATION-EXECUTOR.1
edge: ← satisfies from CAP-SVC-RBAC-NO-PROJECT
delivered_by_release: R1 — API service foundation (context, RBAC ops, audit, envelope)
<<<
RELATIONS:
- TYPE: Parent
  VALUE: SEC-API
- TYPE: Parent
  VALUE: ARCH-API-RBAC
  ROLE: Satisfies
- TYPE: Parent
  VALUE: CAP-RBAC
  ROLE: Satisfies
- TYPE: Child
  VALUE: RELEASE-rel-r1-service-foundation
  ROLE: Delivers

[REQUIREMENT]
UID: CAP-SVC-OPERATION-EXECUTOR.1
STATUS: Active
TITLE: Operation executor (authorize → execute → audit → log)
STATEMENT: >>>
runOperation enforces RBAC + project scope, writes audit_events, structured logs, returns ServiceResult.
<<<
COMMENT: >>>
KIND: capability
BASE_UID: CAP-SVC-OPERATION-EXECUTOR
VERSION_N: 1
priority: 10
iteration: iter-r1
security.catalog_ref: CM-2
security.verification_note: Pin mint: inheritable AC-3, AU-2, AU-12 for uses inheritance seed bed.
edge: ← uses from CAP-SVC-OPERATION-ROUTE
edge: ← uses from CAP-UI-FRAME.1
edge: ← uses from CAP-UI-FRAME.2
in_scope_of_contract: ReqALM product (build)
edge: → conforms_to to AC-3 (pin imprint=nist-800-53@rev5-dogfood-20261006 inheritable)
edge: → conforms_to to AU-2 (pin imprint=nist-800-53@rev5-dogfood-20261006 inheritable)
edge: → conforms_to to AU-12 (pin imprint=nist-800-53@rev5-dogfood-20261006 inheritable)
<<<
RELATIONS:
- TYPE: Parent
  VALUE: SEC-API
- TYPE: Parent
  VALUE: CAP-SVC-OPERATION-EXECUTOR
  ROLE: Refines
- TYPE: Parent
  VALUE: ARCH-API-RBAC
  ROLE: Satisfies
- TYPE: Parent
  VALUE: CAP-RBAC
  ROLE: Satisfies
- TYPE: Parent
  VALUE: AC-3
  ROLE: ConformsTo
- TYPE: Parent
  VALUE: AU-2
  ROLE: ConformsTo
- TYPE: Parent
  VALUE: AU-12
  ROLE: ConformsTo
- TYPE: Child
  VALUE: CONTRACT-ctr-reqalm-product
  ROLE: InScopeOf

[REQUIREMENT]
UID: CAP-SVC-AUDIT-APPEND
STATUS: Active
TITLE: Append-only business audit_events table
STATEMENT: >>>
Migration 006 + writeBusinessAudit; auth events remain in auth_audit_events.
<<<
COMMENT: >>>
KIND: capability
BASE_UID: CAP-SVC-AUDIT-APPEND
VERSION_N: 0
priority: 10
iteration: iter-r1
security.catalog_ref: CM-2
security.verification_note: Planned until service-foundation PR merges.
edge: ← uses from ARCH-ATTACH-AUDIT
in_scope_of_contract: ReqALM product (build)
delivered_by_release: R1 — API service foundation (context, RBAC ops, audit, envelope)
<<<
RELATIONS:
- TYPE: Parent
  VALUE: SEC-API
- TYPE: Child
  VALUE: CONTRACT-ctr-reqalm-product
  ROLE: InScopeOf
- TYPE: Child
  VALUE: RELEASE-rel-r1-service-foundation
  ROLE: Delivers

[REQUIREMENT]
UID: CAP-SVC-STRUCTURED-LOG
STATUS: Active
TITLE: Structured operation logging with redaction
STATEMENT: >>>
logOperation + redactForLog; secrets/tokens/password keys redacted in log payloads.
<<<
COMMENT: >>>
KIND: capability
BASE_UID: CAP-SVC-STRUCTURED-LOG
VERSION_N: 0
priority: 10
iteration: iter-r1
security.catalog_ref: CM-2
security.verification_note: Planned until service-foundation PR merges.
edge: ← uses from ARCH-ATTACH-SCOPE
edge: ← uses from ARCH-ATTACH-SCOPE.1
in_scope_of_contract: ReqALM product (build)
delivered_by_release: R1 — API service foundation (context, RBAC ops, audit, envelope)
<<<
RELATIONS:
- TYPE: Parent
  VALUE: SEC-API
- TYPE: Child
  VALUE: CONTRACT-ctr-reqalm-product
  ROLE: InScopeOf
- TYPE: Child
  VALUE: RELEASE-rel-r1-service-foundation
  ROLE: Delivers

[REQUIREMENT]
UID: CAP-SVC-ROUTE-REGISTRY
STATUS: Active
TITLE: Fail-closed API route security registration
STATEMENT: >>>
Every /api /oauth /mcp /health /ready route declares public, authenticated, or permission; test enforces.
<<<
COMMENT: >>>
KIND: capability
BASE_UID: CAP-SVC-ROUTE-REGISTRY
VERSION_N: 0
priority: 10
iteration: iter-r1
security.catalog_ref: CM-2
security.verification_note: Planned until service-foundation PR merges.
edge: ← satisfies from CAP-SVC-BUSINESS-ROUTE-AUDIT
edge: ← refines from CAP-SVC-IMPLICIT-PUBLIC-EXACT
edge: ← refines from CAP-SVC-NON-API-AUTH-AUDIT
in_scope_of_contract: ReqALM product (build)
delivered_by_release: R1 — API service foundation (context, RBAC ops, audit, envelope)
<<<
RELATIONS:
- TYPE: Parent
  VALUE: SEC-API
- TYPE: Parent
  VALUE: ARCH-API-RBAC
  ROLE: Satisfies
- TYPE: Child
  VALUE: CONTRACT-ctr-reqalm-product
  ROLE: InScopeOf
- TYPE: Child
  VALUE: RELEASE-rel-r1-service-foundation
  ROLE: Delivers

[REQUIREMENT]
UID: CAP-SVC-MODULE-BOOTSTRAP
STATUS: Active
TITLE: Feature module convention + registration
STATEMENT: >>>
src/modules/<feature>/ with service, routes, tests; register.ts entrypoint and README.
<<<
COMMENT: >>>
KIND: capability
BASE_UID: CAP-SVC-MODULE-BOOTSTRAP
VERSION_N: 0
priority: 10
iteration: iter-r1
security.catalog_ref: CM-2
security.verification_note: Planned until service-foundation PR merges.
in_scope_of_contract: ReqALM product (build)
delivered_by_release: R1 — API service foundation (context, RBAC ops, audit, envelope)
<<<
RELATIONS:
- TYPE: Parent
  VALUE: SEC-API
- TYPE: Parent
  VALUE: ARCH-API-LAYERS
  ROLE: Satisfies
- TYPE: Child
  VALUE: CONTRACT-ctr-reqalm-product
  ROLE: InScopeOf
- TYPE: Child
  VALUE: RELEASE-rel-r1-service-foundation
  ROLE: Delivers

[REQUIREMENT]
UID: CAP-SVC-PROJECT-READ
STATUS: Active
TITLE: Reference vertical GET /api/v1/projects/:projectId
STATEMENT: >>>
Project read gated on requirement:read, project-scoped 404 without grant, enveloped response, audited.
<<<
COMMENT: >>>
KIND: capability
BASE_UID: CAP-SVC-PROJECT-READ
VERSION_N: 0
priority: 10
iteration: iter-r1
security.catalog_ref: CM-2
security.verification_note: Planned until service-foundation PR merges.
edge: ← satisfies from CAP-BROWSE-CP
in_scope_of_contract: ReqALM product (build)
delivered_by_release: R1 — API service foundation (context, RBAC ops, audit, envelope)
<<<
RELATIONS:
- TYPE: Parent
  VALUE: SEC-API
- TYPE: Parent
  VALUE: ARCH-API-RBAC
  ROLE: Satisfies
- TYPE: Child
  VALUE: CONTRACT-ctr-reqalm-product
  ROLE: InScopeOf
- TYPE: Child
  VALUE: RELEASE-rel-r1-service-foundation
  ROLE: Delivers

[REQUIREMENT]
UID: ARCH-OTEL-TRACE
STATUS: Draft
TITLE: Distributed tracing (W3C, operation + dependency spans)
STATEMENT: >>>
Distributed tracing spans the HTTP route, service operation (runOperation), and dependencies (PostgreSQL via pg auto-instrumentation, OpenBao/undici fetch). W3C traceparent is continued on ingress. Structured logs and append-only audit_events carry trace_id for correlation. Span attributes never include secrets, tokens, or password material.
<<<
COMMENT: >>>
KIND: requirement
BASE_UID: ARCH-OTEL-TRACE
VERSION_N: 0
priority: 22
iteration: iter-r1
security.catalog_ref: AU-3
security.verification_note: Trace/log/audit correlation; OTLP traces export (not ARCH-OTEL audit-event export).
edge: ← satisfies from CAP-OTEL-SDK-BOOTSTRAP
edge: ← satisfies from CAP-OTEL-W3C-CONTEXT
edge: ← satisfies from CAP-OTEL-OPERATION-SPANS
edge: ← satisfies from CAP-OTEL-KEY-DEP
edge: ← satisfies from CAP-OTEL-AUDIT-TRACE
edge: ← satisfies from CAP-OTEL-EXPORT
edge: ← satisfies from CAP-OTEL-TEST-HARNESS
edge: ← satisfies from CAP-OTEL-SPAN-SAFE-ERRORS
in_scope_of_contract: ReqALM product (build)
<<<
RELATIONS:
- TYPE: Parent
  VALUE: SEC-API
- TYPE: Parent
  VALUE: ARCH-OTEL
  ROLE: Uses
- TYPE: Child
  VALUE: CONTRACT-ctr-reqalm-product
  ROLE: InScopeOf

[REQUIREMENT]
UID: CAP-OTEL-SDK-BOOTSTRAP
STATUS: Active
TITLE: OpenTelemetry SDK bootstrap (HTTP, Fastify, pg, undici)
STATEMENT: >>>
Register hook (sdk-trace-node tracer provider, OTLP/HTTP trace exporter only) loads before app modules; off by default with no SDK loaded; http, Fastify, pg and undici instrumentation shared with tests.
<<<
COMMENT: >>>
KIND: capability
BASE_UID: CAP-OTEL-SDK-BOOTSTRAP
VERSION_N: 0
priority: 10
iteration: iter-r1
security.catalog_ref: CM-2
security.verification_note: Planned until OTel tracing PR merges.
in_scope_of_contract: ReqALM product (build)
delivered_by_release: R1 — OpenTelemetry tracing (W3C, operation + dependency spans)
<<<
RELATIONS:
- TYPE: Parent
  VALUE: SEC-API
- TYPE: Parent
  VALUE: ARCH-OTEL-TRACE
  ROLE: Satisfies
- TYPE: Child
  VALUE: CONTRACT-ctr-reqalm-product
  ROLE: InScopeOf
- TYPE: Child
  VALUE: RELEASE-rel-r1-otel-tracing
  ROLE: Delivers

[REQUIREMENT]
UID: CAP-OTEL-W3C-CONTEXT
STATUS: Active
TITLE: W3C trace context and validated request id
STATEMENT: >>>
Continues traceparent; x-request-id validated (printable, ≤128) else UUID; trace_id on RequestContext and logs.
<<<
COMMENT: >>>
KIND: capability
BASE_UID: CAP-OTEL-W3C-CONTEXT
VERSION_N: 0
priority: 10
iteration: iter-r1
security.catalog_ref: CM-2
security.verification_note: Planned until OTel tracing PR merges.
in_scope_of_contract: ReqALM product (build)
delivered_by_release: R1 — OpenTelemetry tracing (W3C, operation + dependency spans)
<<<
RELATIONS:
- TYPE: Parent
  VALUE: SEC-API
- TYPE: Parent
  VALUE: ARCH-OTEL-TRACE
  ROLE: Satisfies
- TYPE: Child
  VALUE: CONTRACT-ctr-reqalm-product
  ROLE: InScopeOf
- TYPE: Child
  VALUE: RELEASE-rel-r1-otel-tracing
  ROLE: Delivers

[REQUIREMENT]
UID: CAP-OTEL-OPERATION-SPANS
STATUS: Active
TITLE: Manual operation spans (runOperation)
STATEMENT: >>>
Operation span with RBAC/outcome attributes; error status on deny/error; no secrets in attributes.
<<<
COMMENT: >>>
KIND: capability
BASE_UID: CAP-OTEL-OPERATION-SPANS
VERSION_N: 0
priority: 10
iteration: iter-r1
security.catalog_ref: CM-2
security.verification_note: Planned until OTel tracing PR merges.
edge: ← refines from CAP-OTEL-SPAN-SAFE-ERRORS
in_scope_of_contract: ReqALM product (build)
delivered_by_release: R1 — OpenTelemetry tracing (W3C, operation + dependency spans)
<<<
RELATIONS:
- TYPE: Parent
  VALUE: SEC-API
- TYPE: Parent
  VALUE: ARCH-OTEL-TRACE
  ROLE: Satisfies
- TYPE: Child
  VALUE: CONTRACT-ctr-reqalm-product
  ROLE: InScopeOf
- TYPE: Child
  VALUE: RELEASE-rel-r1-otel-tracing
  ROLE: Delivers

[REQUIREMENT]
UID: CAP-OTEL-KEY-DEP
STATUS: Active
TITLE: OpenBao dependency spans (KeyProvider)
STATEMENT: >>>
KeyProvider calls emit key.* spans (dependency and purpose only; no key material or tokens) without changing the KeyProvider interface; the OpenBao HTTP calls are their undici-instrumented child spans.
<<<
COMMENT: >>>
KIND: capability
BASE_UID: CAP-OTEL-KEY-DEP
VERSION_N: 0
priority: 10
iteration: iter-r1
security.catalog_ref: CM-2
security.verification_note: Planned until OTel tracing PR merges.
in_scope_of_contract: ReqALM product (build)
delivered_by_release: R1 — OpenTelemetry tracing (W3C, operation + dependency spans)
<<<
RELATIONS:
- TYPE: Parent
  VALUE: SEC-API
- TYPE: Parent
  VALUE: ARCH-OTEL-TRACE
  ROLE: Satisfies
- TYPE: Child
  VALUE: CONTRACT-ctr-reqalm-product
  ROLE: InScopeOf
- TYPE: Child
  VALUE: RELEASE-rel-r1-otel-tracing
  ROLE: Delivers

[REQUIREMENT]
UID: CAP-OTEL-AUDIT-TRACE
STATUS: Active
TITLE: Audit trace_id correlation
STATEMENT: >>>
Migration 007 adds audit_events.trace_id; runOperation writes trace_id on append-only audit rows.
<<<
COMMENT: >>>
KIND: capability
BASE_UID: CAP-OTEL-AUDIT-TRACE
VERSION_N: 0
priority: 10
iteration: iter-r1
security.catalog_ref: CM-2
security.verification_note: Planned until OTel tracing PR merges.
in_scope_of_contract: ReqALM product (build)
delivered_by_release: R1 — OpenTelemetry tracing (W3C, operation + dependency spans)
<<<
RELATIONS:
- TYPE: Parent
  VALUE: SEC-API
- TYPE: Parent
  VALUE: ARCH-OTEL-TRACE
  ROLE: Satisfies
- TYPE: Child
  VALUE: CONTRACT-ctr-reqalm-product
  ROLE: InScopeOf
- TYPE: Child
  VALUE: RELEASE-rel-r1-otel-tracing
  ROLE: Delivers

[REQUIREMENT]
UID: CAP-OTEL-EXPORT
STATUS: Active
TITLE: OTLP trace export (opt-in)
STATEMENT: >>>
OTEL_EXPORTER_OTLP_ENDPOINT / OTEL_SERVICE_NAME; documented local collector binding.
<<<
COMMENT: >>>
KIND: capability
BASE_UID: CAP-OTEL-EXPORT
VERSION_N: 0
priority: 10
iteration: iter-r1
security.catalog_ref: CM-2
security.verification_note: Planned until OTel tracing PR merges.
in_scope_of_contract: ReqALM product (build)
delivered_by_release: R1 — OpenTelemetry tracing (W3C, operation + dependency spans)
<<<
RELATIONS:
- TYPE: Parent
  VALUE: SEC-API
- TYPE: Parent
  VALUE: ARCH-OTEL-TRACE
  ROLE: Satisfies
- TYPE: Child
  VALUE: CONTRACT-ctr-reqalm-product
  ROLE: InScopeOf
- TYPE: Child
  VALUE: RELEASE-rel-r1-otel-tracing
  ROLE: Delivers

[REQUIREMENT]
UID: CAP-OTEL-TEST-HARNESS
STATUS: Active
TITLE: In-process tracing tests (real pg + PGlite socket)
STATEMENT: >>>
otel-preload starts the test SDK with the production instrumentation list before pg is imported; real pg Pool over PGLiteSocketServer; in-memory exporter assertions.
<<<
COMMENT: >>>
KIND: capability
BASE_UID: CAP-OTEL-TEST-HARNESS
VERSION_N: 0
priority: 10
iteration: iter-r1
security.catalog_ref: CM-2
security.verification_note: Planned until OTel tracing PR merges.
in_scope_of_contract: ReqALM product (build)
delivered_by_release: R1 — OpenTelemetry tracing (W3C, operation + dependency spans)
<<<
RELATIONS:
- TYPE: Parent
  VALUE: SEC-API
- TYPE: Parent
  VALUE: ARCH-OTEL-TRACE
  ROLE: Satisfies
- TYPE: Child
  VALUE: CONTRACT-ctr-reqalm-product
  ROLE: InScopeOf
- TYPE: Child
  VALUE: RELEASE-rel-r1-otel-tracing
  ROLE: Delivers

[REQUIREMENT]
UID: CAP-SVC-OPERATION-ROUTE
STATUS: Active
TITLE: defineOperationRoute — single pipeline for /api/ business routes
STATEMENT: >>>
Business routes under /api/ register only via defineOperationRoute, which runs authenticate, project scope, permission, parseInput, execute, append-only audit_events, log, in that order. Project scope comes from the :projectId path param, parsed before any input validation; an unparsable id is not_found, identical to a missing or ungranted project, and the validated input must name the same project. parseInput validates params/query/body once (Zod); validation failures, including unreadable bodies, reach only authenticated, in-scope, authorized callers, are audited without input values, and answer Problem Details (application/problem+json); unexpected throws are a 500 without the error message. reqalmSecurity is derived from the operation; registration throws unless the operation declares a permission bound to a project (projectScoped + projectIdFromInput + :projectId path param) or authenticatedOnly.
<<<
COMMENT: >>>
KIND: capability
BASE_UID: CAP-SVC-OPERATION-ROUTE
VERSION_N: 0
priority: 10
iteration: iter-r1
security.catalog_ref: CM-2
security.verification_note: Planned until operation-route PR merges.
edge: ← refines from CAP-SVC-PROJECT-ID-SLUG
edge: ← satisfies from CAP-READ-REQS
edge: ← satisfies from CAP-READ-RELEASES
edge: ← satisfies from CAP-READ-HIERARCHY
edge: ← satisfies from CAP-RELATIONS-API
edge: ← satisfies from CAP-CATALOGS-API
edge: ← satisfies from CAP-CONTRACTS-LOADER
edge: ← satisfies from CAP-READ-CONTRACTS
edge: ← satisfies from CAP-READ-ACCESS
in_scope_of_contract: ReqALM product (build)
delivered_by_release: R1 — defineOperationRoute (single business-route pipeline)
<<<
RELATIONS:
- TYPE: Parent
  VALUE: SEC-API
- TYPE: Parent
  VALUE: ARCH-API-LAYERS
  ROLE: Satisfies
- TYPE: Parent
  VALUE: ARCH-API-RBAC
  ROLE: Satisfies
- TYPE: Parent
  VALUE: CAP-SVC-OPERATION-EXECUTOR.1
  ROLE: Uses
- TYPE: Child
  VALUE: CONTRACT-ctr-reqalm-product
  ROLE: InScopeOf
- TYPE: Child
  VALUE: RELEASE-rel-r1-route-helper
  ROLE: Delivers

[REQUIREMENT]
UID: CAP-SVC-BUSINESS-ROUTE-AUDIT
STATUS: Active
TITLE: Fail-closed business route registration test
STATEMENT: >>>
route-security.test.ts rejects /api/ routes not registered via defineOperationRoute (exact METHOD + path allowlist for auth/OAuth-shaped and dev seed routes), permission markers on any hand-registered route, and reqalmSecurity markers that disagree with the operation.
<<<
COMMENT: >>>
KIND: capability
BASE_UID: CAP-SVC-BUSINESS-ROUTE-AUDIT
VERSION_N: 0
priority: 10
iteration: iter-r1
security.catalog_ref: CM-2
security.verification_note: Planned until operation-route PR merges.
edge: ← refines from CAP-SVC-IMPLICIT-PUBLIC-EXACT
in_scope_of_contract: ReqALM product (build)
delivered_by_release: R1 — defineOperationRoute (single business-route pipeline)
<<<
RELATIONS:
- TYPE: Parent
  VALUE: SEC-API
- TYPE: Parent
  VALUE: CAP-SVC-ROUTE-REGISTRY
  ROLE: Satisfies
- TYPE: Parent
  VALUE: ARCH-API-RBAC
  ROLE: Satisfies
- TYPE: Child
  VALUE: CONTRACT-ctr-reqalm-product
  ROLE: InScopeOf
- TYPE: Child
  VALUE: RELEASE-rel-r1-route-helper
  ROLE: Delivers

[REQUIREMENT]
UID: CAP-SVC-PROBLEM-JSON
STATUS: Active
TITLE: Problem Details content type on service errors
STATEMENT: >>>
Error responses from operation routes and from unknown /api/ paths are Problem Details with Content-Type application/problem+json and the request id, as documented in the static OpenAPI spec.
<<<
COMMENT: >>>
KIND: capability
BASE_UID: CAP-SVC-PROBLEM-JSON
VERSION_N: 0
priority: 10
iteration: iter-r1
security.catalog_ref: CM-2
security.verification_note: Planned until operation-route PR merges.
in_scope_of_contract: ReqALM product (build)
delivered_by_release: R1 — defineOperationRoute (single business-route pipeline)
<<<
RELATIONS:
- TYPE: Parent
  VALUE: SEC-API
- TYPE: Parent
  VALUE: CAP-SVC-RESULT-ENVELOPE
  ROLE: Satisfies
- TYPE: Child
  VALUE: CONTRACT-ctr-reqalm-product
  ROLE: InScopeOf
- TYPE: Child
  VALUE: RELEASE-rel-r1-route-helper
  ROLE: Delivers

[REQUIREMENT]
UID: CAP-SVC-PROJECT-ID-SLUG
STATUS: Active
TITLE: Project id path param slug validation
STATEMENT: >>>
The :projectId path param must match ^[a-z0-9][a-z0-9-]{0,63}$ before it becomes project scope. An id that does not (padded, control characters, uppercase, over-long at any length) is not_found after authentication, identical to a missing or ungranted project, and an unauthenticated caller gets the same 401 as for a valid id, before any validation detail. An invalid id is never recorded raw: audit_events.project_id is NULL, no reqalm.project_id span attribute is set, and request logs and exported span URL attributes show the segment as [invalid].
<<<
COMMENT: >>>
KIND: capability
BASE_UID: CAP-SVC-PROJECT-ID-SLUG
VERSION_N: 0
priority: 10
iteration: iter-r1
security.catalog_ref: CM-2
security.verification_note: Planned until route-hardening PR merges.
in_scope_of_contract: ReqALM product (build)
delivered_by_release: R1 — route helper hardening (Cyber/QA follow-up)
<<<
RELATIONS:
- TYPE: Parent
  VALUE: SEC-API
- TYPE: Parent
  VALUE: ARCH-API-RBAC
  ROLE: Satisfies
- TYPE: Parent
  VALUE: CAP-SVC-OPERATION-ROUTE
  ROLE: Refines
- TYPE: Child
  VALUE: CONTRACT-ctr-reqalm-product
  ROLE: InScopeOf
- TYPE: Child
  VALUE: RELEASE-rel-r1-route-hardening
  ROLE: Delivers

[REQUIREMENT]
UID: CAP-SVC-STATIC-DEP-PATCH
STATUS: Active
TITLE: Production @fastify/static dependency patch
STATEMENT: >>>
apps/reqalm resolves @fastify/static 10.1.5 both directly (^10.1.5) and through @fastify/swagger-ui 6.1.1 (^10.1.0), with no pnpm override, so GHSA-83w8-p2f5-377r and GHSA-8pvw-jcv7-9cmj (and GHSA-pr96-94w5-mx2h, GHSA-x428-ghpx-8j92) are gone from pnpm audit --prod; the web bundle and /docs still serve, and encoded path-traversal requests never return file contents.
<<<
COMMENT: >>>
KIND: capability
BASE_UID: CAP-SVC-STATIC-DEP-PATCH
VERSION_N: 0
priority: 10
iteration: iter-r1
security.catalog_ref: CM-2
security.verification_note: Planned until route-hardening PR merges.
in_scope_of_contract: ReqALM product (build)
delivered_by_release: R1 — route helper hardening (Cyber/QA follow-up)
<<<
RELATIONS:
- TYPE: Parent
  VALUE: SEC-API
- TYPE: Parent
  VALUE: ARCH-DEPLOY-MINIMAL
  ROLE: Satisfies
- TYPE: Child
  VALUE: CONTRACT-ctr-reqalm-product
  ROLE: InScopeOf
- TYPE: Child
  VALUE: RELEASE-rel-r1-route-hardening
  ROLE: Delivers

[REQUIREMENT]
UID: CAP-OTEL-SPAN-SAFE-ERRORS
STATUS: Active
TITLE: Span errors without raw exception text
STATEMENT: >>>
Every exported span (operation, Fastify request and handler, http, pg, undici, OpenBao) reports a failure as ERROR status with the generic message 'operation failed'; exception events keep only exception.type (no message or stack); operation spans add reqalm.error_kind (service error code or internal). Raw exception and database text stays in the server log only.
<<<
COMMENT: >>>
KIND: capability
BASE_UID: CAP-OTEL-SPAN-SAFE-ERRORS
VERSION_N: 0
priority: 10
iteration: iter-r1
security.catalog_ref: CM-2
security.verification_note: Planned until route-hardening PR merges.
in_scope_of_contract: ReqALM product (build)
delivered_by_release: R1 — route helper hardening (Cyber/QA follow-up)
<<<
RELATIONS:
- TYPE: Parent
  VALUE: SEC-API
- TYPE: Parent
  VALUE: CAP-OTEL-OPERATION-SPANS
  ROLE: Refines
- TYPE: Parent
  VALUE: ARCH-OTEL-TRACE
  ROLE: Satisfies
- TYPE: Child
  VALUE: CONTRACT-ctr-reqalm-product
  ROLE: InScopeOf
- TYPE: Child
  VALUE: RELEASE-rel-r1-route-hardening
  ROLE: Delivers

[REQUIREMENT]
UID: CAP-SVC-IMPLICIT-PUBLIC-EXACT
STATUS: Active
TITLE: Implicit public route allowlist is method+path exact
STATEMENT: >>>
OAuth, probe, and auth-shaped routes become implicitly public only when METHOD and path match the exact allowlist (HEAD checked as GET; /docs for GET and HEAD only), and a route registered for several methods only if every method matches; any other method or path must declare reqalmSecurity.
<<<
COMMENT: >>>
KIND: capability
BASE_UID: CAP-SVC-IMPLICIT-PUBLIC-EXACT
VERSION_N: 0
priority: 10
iteration: iter-r1
security.catalog_ref: CM-2
security.verification_note: Planned until route-hardening PR merges.
in_scope_of_contract: ReqALM product (build)
delivered_by_release: R1 — route helper hardening (Cyber/QA follow-up)
<<<
RELATIONS:
- TYPE: Parent
  VALUE: SEC-API
- TYPE: Parent
  VALUE: CAP-SVC-ROUTE-REGISTRY
  ROLE: Refines
- TYPE: Parent
  VALUE: CAP-SVC-BUSINESS-ROUTE-AUDIT
  ROLE: Refines
- TYPE: Parent
  VALUE: ARCH-API-RBAC
  ROLE: Satisfies
- TYPE: Child
  VALUE: CONTRACT-ctr-reqalm-product
  ROLE: InScopeOf
- TYPE: Child
  VALUE: RELEASE-rel-r1-route-hardening
  ROLE: Delivers

[REQUIREMENT]
UID: CAP-SVC-NON-API-AUTH-AUDIT
STATUS: Active
TITLE: Authenticated non-/api routes audited or allowlisted
STATEMENT: >>>
Hand-registered authenticated routes outside /api/ must use defineOperationRoute or sit on an exact METHOD + path allowlist (today only POST /mcp); route-security.test.ts fails closed otherwise.
<<<
COMMENT: >>>
KIND: capability
BASE_UID: CAP-SVC-NON-API-AUTH-AUDIT
VERSION_N: 0
priority: 10
iteration: iter-r1
security.catalog_ref: CM-2
security.verification_note: Planned until route-hardening PR merges.
in_scope_of_contract: ReqALM product (build)
delivered_by_release: R1 — route helper hardening (Cyber/QA follow-up)
<<<
RELATIONS:
- TYPE: Parent
  VALUE: SEC-API
- TYPE: Parent
  VALUE: CAP-SVC-ROUTE-REGISTRY
  ROLE: Refines
- TYPE: Parent
  VALUE: ARCH-API-RBAC
  ROLE: Satisfies
- TYPE: Child
  VALUE: CONTRACT-ctr-reqalm-product
  ROLE: InScopeOf
- TYPE: Child
  VALUE: RELEASE-rel-r1-route-hardening
  ROLE: Delivers

[REQUIREMENT]
UID: ARCH-WRITE-UOW-AUDIT
STATUS: Active
TITLE: Write unit-of-work with audit
STATEMENT: >>>
Mutating domain operations shall run inside a unit-of-work boundary that appends audit events atomically with business writes.
<<<
COMMENT: >>>
KIND: requirement
BASE_UID: ARCH-WRITE-UOW-AUDIT
VERSION_N: 0
priority: 15
iteration: iter-r1
security.catalog_ref: AU-9
security.verification_note: Groomed 2026-10-09; pre-write or UI track.
edge: ← uses from ARCH-ATTACH-AUDIT
in_scope_of_contract: ReqALM product (build)
<<<
RELATIONS:
- TYPE: Parent
  VALUE: SEC-API
- TYPE: Parent
  VALUE: ARCH-OTEL
  ROLE: Refines
- TYPE: Child
  VALUE: CONTRACT-ctr-reqalm-product
  ROLE: InScopeOf

[REQUIREMENT]
UID: ARCH-WRITE-REPOSITORY-LAYER
STATUS: Active
TITLE: Repository layer (no SQL in routes)
STATEMENT: >>>
HTTP route adapters shall not embed SQL; persistence shall go through a repository layer invoked from the unit-of-work boundary.
<<<
COMMENT: >>>
KIND: requirement
BASE_UID: ARCH-WRITE-REPOSITORY-LAYER
VERSION_N: 0
priority: 15
iteration: iter-r1
security.catalog_ref: CM-2
security.verification_note: Groomed 2026-10-09; pre-write or UI track.
in_scope_of_contract: ReqALM product (build)
<<<
RELATIONS:
- TYPE: Parent
  VALUE: SEC-API
- TYPE: Parent
  VALUE: ARCH-API-LAYERS
  ROLE: Refines
- TYPE: Child
  VALUE: CONTRACT-ctr-reqalm-product
  ROLE: InScopeOf

[REQUIREMENT]
UID: ARCH-WRITE-TRUNCATE-GUARD
STATUS: Active
TITLE: TRUNCATE guard and runtime DB role
STATEMENT: >>>
The database shall install a TRUNCATE guard (trigger or equivalent) and the runtime application DB role shall not be table owner, curbing destructive SQL from compromised credentials.
<<<
COMMENT: >>>
KIND: requirement
BASE_UID: ARCH-WRITE-TRUNCATE-GUARD
VERSION_N: 0
priority: 15
iteration: iter-r1
security.catalog_ref: CM-6
security.verification_note: Groomed 2026-10-09; pre-write or UI track.
in_scope_of_contract: ReqALM product (build)
<<<
RELATIONS:
- TYPE: Parent
  VALUE: SEC-API
- TYPE: Parent
  VALUE: ARCH-CP-SCOPE
  ROLE: Refines
- TYPE: Child
  VALUE: CONTRACT-ctr-reqalm-product
  ROLE: InScopeOf

[REQUIREMENT]
UID: ARCH-WRITE-AUDIT-FLOOD
STATUS: Active
TITLE: Audit append flood controls
STATEMENT: >>>
Audit append endpoints shall require authentication or rate limiting so unauthenticated callers cannot flood audit storage.
<<<
COMMENT: >>>
KIND: requirement
BASE_UID: ARCH-WRITE-AUDIT-FLOOD
VERSION_N: 0
priority: 15
iteration: iter-r1
security.catalog_ref: AU-9
security.verification_note: Groomed 2026-10-09; pre-write or UI track.
edge: ← uses from ARCH-ATTACH-AUDIT
in_scope_of_contract: ReqALM product (build)
<<<
RELATIONS:
- TYPE: Parent
  VALUE: SEC-API
- TYPE: Parent
  VALUE: ARCH-OTEL
  ROLE: Refines
- TYPE: Child
  VALUE: CONTRACT-ctr-reqalm-product
  ROLE: InScopeOf

[REQUIREMENT]
UID: ARCH-WRITE-VERSION-UNIQUE
STATUS: Active
TITLE: Unique requirement version constraint
STATEMENT: >>>
The schema shall enforce UNIQUE (project_id, base_uid, version_n) on requirement versions.
<<<
COMMENT: >>>
KIND: requirement
BASE_UID: ARCH-WRITE-VERSION-UNIQUE
VERSION_N: 0
priority: 15
iteration: iter-r1
security.catalog_ref: CM-2
security.verification_note: Groomed 2026-10-09; pre-write or UI track.
in_scope_of_contract: ReqALM product (build)
<<<
RELATIONS:
- TYPE: Parent
  VALUE: SEC-API
- TYPE: Parent
  VALUE: ARCH-VER
  ROLE: Refines
- TYPE: Child
  VALUE: CONTRACT-ctr-reqalm-product
  ROLE: InScopeOf

[REQUIREMENT]
UID: ARCH-WRITE-RESERVED-IDS
STATUS: Active
TITLE: Reject reserved id segments at mint
STATEMENT: >>>
Minting requirement or capability ids shall reject reserved path segments defined by the product id policy.
<<<
COMMENT: >>>
KIND: requirement
BASE_UID: ARCH-WRITE-RESERVED-IDS
VERSION_N: 0
priority: 15
iteration: iter-r1
security.catalog_ref: CM-2
security.verification_note: Groomed 2026-10-09; pre-write or UI track.
in_scope_of_contract: ReqALM product (build)
<<<
RELATIONS:
- TYPE: Parent
  VALUE: SEC-API
- TYPE: Parent
  VALUE: ARCH-MINT-KIND
  ROLE: Refines
- TYPE: Child
  VALUE: CONTRACT-ctr-reqalm-product
  ROLE: InScopeOf

[[/SECTION]]

[[SECTION]]
UID: SEC-SEC
TITLE: Security / RBAC

[TEXT]
UID: SEC-SEC-INTRO
STATEMENT: >>>
Cross-cutting security controls, NIST/STIG alignment notes, and capability packs for access enforcement.
<<<

[REQUIREMENT]
UID: CAP-SSO
STATUS: Draft
TITLE: Federated SSO session
STATEMENT: >>>
Capability pack for federated SSO session establishment and teardown against the enterprise IdP.
Covers sign-in and sign-out paths used by UI and MCP hosts. No local passwords; MFA and authenticator
policy live at the IdP (NIST IA-2/IA-5, V-222536/542).
<<<
COMMENT: >>>
KIND: capability
BASE_UID: CAP-SSO
VERSION_N: 0
priority: 10
iteration: iter-r0
security.catalog_ref: AC-3
security.verification_note: AC-3 access enforcement; AU-2/3/12 where mutating.
catalog_drift: status=flagged class=normative item=AC-3 from=nist-800-53@rev5-dogfood-20261006 to=nist-800-53@rev5-dogfood-20261006
edge: ← uses from ARCH-DEVENV-IDENTITY
edge: ← uses from ARCH-DEVENV-IDENTITY.1
edge: ← refines from ARCH-AUTH-FEDERATION
edge: ← refines from CAP-SSO.1
in_scope_of_contract: Design-2026-10
in_scope_of_contract: Security package
in_scope_of_contract: Platform baseline
delivered_by_release: R0-sequences
edge: → conforms_to to IA-2 (pin imprint=nist-800-53@rev5-dogfood-20261006)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-SEC
- TYPE: Parent
  VALUE: A01
  ROLE: Satisfies
- TYPE: Parent
  VALUE: A02
  ROLE: Satisfies
- TYPE: Parent
  VALUE: IA-2
  ROLE: ConformsTo
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-design-2026-10
  ROLE: InScopeOf
- TYPE: Child
  VALUE: CONTRACT-contract-security-package
  ROLE: InScopeOf
- TYPE: Child
  VALUE: CONTRACT-contract-platform-baseline
  ROLE: InScopeOf
- TYPE: Child
  VALUE: RELEASE-rel-r0-sequences
  ROLE: Delivers

[REQUIREMENT]
UID: CAP-SSO.1
STATUS: Active
TITLE: Federated SSO session
STATEMENT: >>>
Capability pack for enterprise federated SSO session establishment and teardown (ARCH-AUTH-FEDERATION). R0 delivered sequence diagrams and requirements only; runtime today uses the internal OAuth AS with dev local accounts (ARCH-DEVENV-IDENTITY.1), not upstream IdP federation. MFA for production remains at the enterprise IdP when federation ships.
<<<
COMMENT: >>>
KIND: capability
BASE_UID: CAP-SSO
VERSION_N: 1
priority: 10
iteration: iter-r0
security.catalog_ref: AC-3
security.verification_note: R0 design pack; federation not shipped — do not mark pass until ARCH-AUTH-FEDERATION delivers.
in_scope_of_contract: ReqALM product (build)
edge: → conforms_to to IA-2 (pin imprint=nist-800-53@rev5-dogfood-20261006)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-SEC
- TYPE: Parent
  VALUE: CAP-SSO
  ROLE: Refines
- TYPE: Parent
  VALUE: A01
  ROLE: Satisfies
- TYPE: Parent
  VALUE: A02
  ROLE: Satisfies
- TYPE: Parent
  VALUE: IA-2
  ROLE: ConformsTo
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-ctr-reqalm-product
  ROLE: InScopeOf

[REQUIREMENT]
UID: CAP-SCOPED-VIEW
STATUS: Draft
TITLE: Client Scoped View binding
STATEMENT: >>>
Capability pack for selecting, clearing, and binding Client Scoped View on the server session.
UI App providers consume the bound clientId for navigation guards. Scope change and clear are audited;
server rejects cross-client resource access even if the client id appears in a forged request.
<<<
COMMENT: >>>
KIND: capability
BASE_UID: CAP-SCOPED-VIEW
VERSION_N: 0
priority: 10
iteration: iter-r0
security.catalog_ref: REQALM-SEC-SCOPE
security.verification_note: Server-bound Client Scoped View. ASD STIG V6R4 V-222429 / V-222550.
edge: ← uses from ARCH-CP-SCOPE
edge: ← uses from FIX-DENY-CROSS-CLIENT
edge: ← refines from CAP-SCOPED-VIEW.1
in_scope_of_contract: Design-2026-10
in_scope_of_contract: Security package
in_scope_of_contract: Platform baseline
delivered_by_release: R0-sequences
edge: → conforms_to to V-222429 (pin imprint=asd-stig@v6r4)
edge: → conforms_to to V-222550 (pin imprint=asd-stig@v6r4)
edge: → conforms_to to AC-3 (pin imprint=nist-800-53@rev5-dogfood-20261006)
<<<
RELATIONS:
- TYPE: Parent
  VALUE: SEC-SEC
- TYPE: Parent
  VALUE: A03
  ROLE: Satisfies
- TYPE: Parent
  VALUE: A04
  ROLE: Satisfies
- TYPE: Parent
  VALUE: V-222429
  ROLE: ConformsTo
- TYPE: Parent
  VALUE: V-222550
  ROLE: ConformsTo
- TYPE: Parent
  VALUE: AC-3
  ROLE: ConformsTo
- TYPE: Child
  VALUE: CONTRACT-contract-design-2026-10
  ROLE: InScopeOf
- TYPE: Child
  VALUE: CONTRACT-contract-security-package
  ROLE: InScopeOf
- TYPE: Child
  VALUE: CONTRACT-contract-platform-baseline
  ROLE: InScopeOf
- TYPE: Child
  VALUE: RELEASE-rel-r0-sequences
  ROLE: Delivers

[REQUIREMENT]
UID: CAP-SCOPED-VIEW.1
STATUS: Active
TITLE: Client Scoped View binding
STATEMENT: >>>
Capability pack for Client Scoped View: select, clear, and bind clientId on the server session. Partial R1: grant-scoped browse APIs enforce project/client visibility; full A03/A04 UX and MCP parity remain in core-ALM. Scope changes shall be audited when mutating routes exist.
<<<
COMMENT: >>>
KIND: capability
BASE_UID: CAP-SCOPED-VIEW
VERSION_N: 1
priority: 10
iteration: iter-r0
security.catalog_ref: REQALM-SEC-SCOPE
security.verification_note: Partial: browse read scope shipped; full scoped-view mutate UX not complete.
in_scope_of_contract: ReqALM product (build)
edge: → conforms_to to V-222429 (pin imprint=asd-stig@v6r4)
edge: → conforms_to to V-222550 (pin imprint=asd-stig@v6r4)
edge: → conforms_to to AC-3 (pin imprint=nist-800-53@rev5-dogfood-20261006)
<<<
RELATIONS:
- TYPE: Parent
  VALUE: SEC-SEC
- TYPE: Parent
  VALUE: CAP-SCOPED-VIEW
  ROLE: Refines
- TYPE: Parent
  VALUE: A03
  ROLE: Satisfies
- TYPE: Parent
  VALUE: A04
  ROLE: Satisfies
- TYPE: Parent
  VALUE: V-222429
  ROLE: ConformsTo
- TYPE: Parent
  VALUE: V-222550
  ROLE: ConformsTo
- TYPE: Parent
  VALUE: AC-3
  ROLE: ConformsTo
- TYPE: Child
  VALUE: CONTRACT-ctr-reqalm-product
  ROLE: InScopeOf

[REQUIREMENT]
UID: ARCH-CRED
STATUS: Active
TITLE: Credential store controls
STATEMENT: >>>
Credential store controls cover every credential ReqAML holds or verifies: local passwords, MFA authenticators, OAuth refresh tokens, authorization codes, client secrets, and session identifiers. Credentials are never stored or logged in plaintext. Each one is either one-way hashed (verify-only) or wrapped by the key store (must be usable), per ARCH-KEY.
<<<
COMMENT: >>>
KIND: requirement
BASE_UID: ARCH-CRED
VERSION_N: 0
priority: 5
iteration: iter-r1
security.catalog_ref: IA-5
security.verification_note: IA-5 authenticator management umbrella.
edge: ← uses from ARCH-AUTH-LOCAL
edge: ← refines from ARCH-CRED-HASH
edge: ← refines from ARCH-CRED-POLICY
edge: ← refines from ARCH-CRED-LOCKOUT
edge: ← refines from ARCH-CRED-MFA
edge: ← refines from ARCH-CRED-TOKENS
edge: ← refines from ARCH-CRED-SESSION
edge: ← refines from ARCH-CRED-REAUTH
edge: ← refines from ARCH-CRED-AUDIT
edge: ← uses from ARCH-BUILD-FOUNDATION
edge: ← uses from ARCH-AUTH-LOCAL.1
edge: ← satisfies from CAP-CRED-STORE
in_scope_of_contract: ReqALM product (build)
delivered_by_release: R1 — foundation shell + internal auth
edge: → conforms_to to IA-5 (pin imprint=nist-800-53@rev5-dogfood-20261006)
<<<
RELATIONS:
- TYPE: Parent
  VALUE: SEC-SEC
- TYPE: Parent
  VALUE: IA-5
  ROLE: ConformsTo
- TYPE: Child
  VALUE: CONTRACT-ctr-reqalm-product
  ROLE: InScopeOf
- TYPE: Child
  VALUE: RELEASE-rel-r1-foundation-shell-auth
  ROLE: Delivers

[[SECTION]]
UID: ARCH-CRED-CHILDREN
TITLE: Children of ARCH-CRED

[REQUIREMENT]
UID: ARCH-CRED-HASH
STATUS: Active
TITLE: Passwords stored only as salted approved one-way hashes (configurable params)
STATEMENT: >>>
Local passwords are stored only as salted, approved one-way hashes with a per-credential random salt. Algorithm and cost parameters are configuration, not a hard-coded library: Argon2id where FIPS mode is not required, PBKDF2-HMAC-SHA-256/512 (FIPS-approved) where FIPS-validated crypto is required (ARCH-KEY-FIPS). Each stored hash records its algorithm and parameters, and an outdated hash is re-hashed on the next successful login. Passwords travel only over TLS and are never displayed or logged.
<<<
COMMENT: >>>
KIND: requirement
BASE_UID: ARCH-CRED-HASH
VERSION_N: 0
rbac_op: auth:local:signin
priority: 5
iteration: iter-r1
security.catalog_ref: IA-5.1
security.verification_note: IA-5(1) password-based auth; ASD V-222542 / V-222543 / V-222554 / V-222571.
edge: ← uses from FIX-ALLOW-CRED-HASH-ONLY
edge: ← satisfies from CAP-CRED-STORE
in_scope_of_contract: ReqALM product (build)
delivered_by_release: R1 — foundation shell + internal auth
edge: → conforms_to to IA-5.1 (pin imprint=nist-800-53@rev5-dogfood-20261006)
edge: → conforms_to to SC-13 (pin imprint=nist-800-53@rev5-dogfood-20261006)
edge: → conforms_to to V-222542 (pin imprint=asd-stig@v6r4)
edge: → conforms_to to V-222543 (pin imprint=asd-stig@v6r4)
edge: → conforms_to to V-222554 (pin imprint=asd-stig@v6r4)
edge: → conforms_to to V-222571 (pin imprint=asd-stig@v6r4)
<<<
RELATIONS:
- TYPE: Parent
  VALUE: ARCH-CRED
- TYPE: Parent
  VALUE: ARCH-CRED
  ROLE: Refines
- TYPE: Parent
  VALUE: ARCH-KEY-FIPS
  ROLE: Uses
- TYPE: Parent
  VALUE: IA-5.1
  ROLE: ConformsTo
- TYPE: Parent
  VALUE: SC-13
  ROLE: ConformsTo
- TYPE: Parent
  VALUE: V-222542
  ROLE: ConformsTo
- TYPE: Parent
  VALUE: V-222543
  ROLE: ConformsTo
- TYPE: Parent
  VALUE: V-222554
  ROLE: ConformsTo
- TYPE: Parent
  VALUE: V-222571
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-CRED-POLICY
STATUS: Active
TITLE: Password / authenticator policy presets
STATEMENT: >>>
Password and authenticator policy (minimum length, composition or blocklist, change distance, minimum and maximum lifetime, reuse history, temporary password with forced change) is a configurable preset per deployment. The DoD-facing preset meets ASD STIG V6R4 values. Default and seeded credentials must be changed before first use, and production must not contain any.
<<<
COMMENT: >>>
KIND: requirement
BASE_UID: ARCH-CRED-POLICY
VERSION_N: 0
rbac_op: auth:policy:configure
priority: 10
iteration: iter-r1
security.catalog_ref: IA-5.1
security.verification_note: IA-5(1); ASD V-222536..V-222541, V-222544..V-222548, V-222662.
edge: ← uses from FIX-DENY-DEVENV-PROD-LOGIN.1
edge: ← uses from ARCH-AUTH-PROFILE
edge: ← satisfies from CAP-CRED-STORE
in_scope_of_contract: ReqALM product (build)
delivered_by_release: R1 — foundation shell + internal auth
edge: → conforms_to to IA-5.1 (pin imprint=nist-800-53@rev5-dogfood-20261006)
edge: → conforms_to to V-222536 (pin imprint=asd-stig@v6r4)
edge: → conforms_to to V-222537 (pin imprint=asd-stig@v6r4)
edge: → conforms_to to V-222538 (pin imprint=asd-stig@v6r4)
edge: → conforms_to to V-222539 (pin imprint=asd-stig@v6r4)
edge: → conforms_to to V-222540 (pin imprint=asd-stig@v6r4)
edge: → conforms_to to V-222541 (pin imprint=asd-stig@v6r4)
edge: → conforms_to to V-222544 (pin imprint=asd-stig@v6r4)
edge: → conforms_to to V-222545 (pin imprint=asd-stig@v6r4)
edge: → conforms_to to V-222546 (pin imprint=asd-stig@v6r4)
edge: → conforms_to to V-222547 (pin imprint=asd-stig@v6r4)
edge: → conforms_to to V-222548 (pin imprint=asd-stig@v6r4)
edge: → conforms_to to V-222662 (pin imprint=asd-stig@v6r4)
<<<
RELATIONS:
- TYPE: Parent
  VALUE: ARCH-CRED
- TYPE: Parent
  VALUE: ARCH-CRED
  ROLE: Refines
- TYPE: Parent
  VALUE: IA-5.1
  ROLE: ConformsTo
- TYPE: Parent
  VALUE: V-222536
  ROLE: ConformsTo
- TYPE: Parent
  VALUE: V-222537
  ROLE: ConformsTo
- TYPE: Parent
  VALUE: V-222538
  ROLE: ConformsTo
- TYPE: Parent
  VALUE: V-222539
  ROLE: ConformsTo
- TYPE: Parent
  VALUE: V-222540
  ROLE: ConformsTo
- TYPE: Parent
  VALUE: V-222541
  ROLE: ConformsTo
- TYPE: Parent
  VALUE: V-222544
  ROLE: ConformsTo
- TYPE: Parent
  VALUE: V-222545
  ROLE: ConformsTo
- TYPE: Parent
  VALUE: V-222546
  ROLE: ConformsTo
- TYPE: Parent
  VALUE: V-222547
  ROLE: ConformsTo
- TYPE: Parent
  VALUE: V-222548
  ROLE: ConformsTo
- TYPE: Parent
  VALUE: V-222662
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-CRED-LOCKOUT
STATUS: Active
TITLE: Throttling and lockout after failed attempts
STATEMENT: >>>
The AS throttles authentication per account and per source, and locks a local account after N consecutive failed attempts within a window (configurable; DoD preset 3 in 15 minutes). While locked, even a correct password is refused with the same generic error, and failures never reveal whether an account exists. Unlock happens only through an approved admin process (auth:account:unlock) or the configured timer. Every failure, lockout, and unlock is audited.
<<<
COMMENT: >>>
KIND: requirement
BASE_UID: ARCH-CRED-LOCKOUT
VERSION_N: 0
rbac_op: auth:local:signin, auth:account:unlock
priority: 5
iteration: iter-r1
security.catalog_ref: AC-7
security.verification_note: AC-7 unsuccessful logon attempts; ASD V-222432 / V-222433 / V-222462.
edge: ← uses from FIX-DENY-LOCKOUT
edge: ← satisfies from CAP-CRED-STORE
edge: ← satisfies from CAP-AUTH-HARDEN
edge: ← satisfies from CAP-TEST-AUTH-ROUTES
edge: ← satisfies from CAP-TEST-AUTH-HYGIENE
edge: ← satisfies from CAP-AUTH-HARDEN.1
in_scope_of_contract: ReqALM product (build)
delivered_by_release: R1 — foundation shell + internal auth
edge: → conforms_to to AC-7 (pin imprint=nist-800-53@rev5-dogfood-20261006)
edge: → conforms_to to V-222432 (pin imprint=asd-stig@v6r4)
edge: → conforms_to to V-222433 (pin imprint=asd-stig@v6r4)
edge: → conforms_to to V-222462 (pin imprint=asd-stig@v6r4)
<<<
RELATIONS:
- TYPE: Parent
  VALUE: ARCH-CRED
- TYPE: Parent
  VALUE: ARCH-CRED
  ROLE: Refines
- TYPE: Parent
  VALUE: ARCH-AUTH-LOCAL.1
  ROLE: Refines
- TYPE: Parent
  VALUE: AC-7
  ROLE: ConformsTo
- TYPE: Parent
  VALUE: V-222432
  ROLE: ConformsTo
- TYPE: Parent
  VALUE: V-222433
  ROLE: ConformsTo
- TYPE: Parent
  VALUE: V-222462
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-CRED-MFA
STATUS: Active
TITLE: MFA for privileged roles
STATEMENT: >>>
Privileged roles must use multi-factor authentication. Privileged means roles holding admin, approve, apply, sign-off, ship, steward, or key-custodian permissions in the permission tree. For local accounts the AS enforces a second factor, with MFA secrets wrapped by the key store. For federated logins the AS requires upstream MFA evidence (amr/acr). A session without MFA cannot perform privileged operations. MFA for non-privileged users is a policy preset; factor types and the confirmed privileged-role list are open questions.
<<<
COMMENT: >>>
KIND: requirement
BASE_UID: ARCH-CRED-MFA
VERSION_N: 0
rbac_op: auth:mfa:verify
priority: 5
iteration: iter-r1
security.catalog_ref: IA-2.1
security.verification_note: IA-2(1) MFA privileged; ASD V-222523 / V-222527.
edge: ← uses from ARCH-AUTH-FEDERATION
edge: ← uses from ARCH-KEY-CUSTODIAN
edge: ← uses from FIX-DENY-PRIV-NO-MFA
edge: ← uses from ARCH-AUTH-LOCAL-BREAKGLASS
edge: ← uses from FIX-ALLOW-BREAKGLASS-LOCAL-ADMIN
edge: ← satisfies from CAP-CRED-STORE
edge: ← satisfies from CAP-MFA-ENROLL
edge: ← satisfies from CAP-TEST-AUTH-ROUTES
edge: ← satisfies from CAP-MFA-QR
in_scope_of_contract: ReqALM product (build)
delivered_by_release: R1 — foundation shell + internal auth
edge: → conforms_to to IA-2.1 (pin imprint=nist-800-53@rev5-dogfood-20261006)
edge: → conforms_to to V-222523 (pin imprint=asd-stig@v6r4)
edge: → conforms_to to V-222527 (pin imprint=asd-stig@v6r4)
<<<
RELATIONS:
- TYPE: Parent
  VALUE: ARCH-CRED
- TYPE: Parent
  VALUE: ARCH-CRED
  ROLE: Refines
- TYPE: Parent
  VALUE: ARCH-KEY-SCOPE
  ROLE: Uses
- TYPE: Parent
  VALUE: IA-2.1
  ROLE: ConformsTo
- TYPE: Parent
  VALUE: V-222523
  ROLE: ConformsTo
- TYPE: Parent
  VALUE: V-222527
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-CRED-TOKENS
STATUS: Active
TITLE: Server-side tokens and client secrets stored hashed
STATEMENT: >>>
Server-side bearer credentials (refresh tokens, authorization codes, confidential-client secrets, MFA recovery codes) are stored only as hashes (keyed hash or one-way hash), compared in constant time, and never retrievable. Secrets ReqAML must present to others (upstream IdP client secret, Azure DevOps connector tokens, SMTP credentials, OTEL sink credentials) are stored encrypted under key-store DEKs (ARCH-KEY-SCOPE) and never returned by APIs.
<<<
COMMENT: >>>
KIND: requirement
BASE_UID: ARCH-CRED-TOKENS
VERSION_N: 0
priority: 5
iteration: iter-r1
security.catalog_ref: IA-5.6
security.verification_note: IA-5(6) protection of authenticators; SC-28(1); ASD V-222542 / V-222588.
edge: ← uses from ARCH-AUTH-REFRESH
edge: ← uses from ARCH-AUTH-CLIENTREG
edge: ← uses from FIX-ALLOW-CRED-HASH-ONLY
edge: ← satisfies from CAP-CRED-STORE
in_scope_of_contract: ReqALM product (build)
delivered_by_release: R1 — foundation shell + internal auth
edge: → conforms_to to IA-5.6 (pin imprint=nist-800-53@rev5-dogfood-20261006)
edge: → conforms_to to SC-28.1 (pin imprint=nist-800-53@rev5-dogfood-20261006)
edge: → conforms_to to V-222542 (pin imprint=asd-stig@v6r4)
<<<
RELATIONS:
- TYPE: Parent
  VALUE: ARCH-CRED
- TYPE: Parent
  VALUE: ARCH-CRED
  ROLE: Refines
- TYPE: Parent
  VALUE: ARCH-KEY-SCOPE
  ROLE: Uses
- TYPE: Parent
  VALUE: M03
  ROLE: Refines
- TYPE: Parent
  VALUE: IA-5.6
  ROLE: ConformsTo
- TYPE: Parent
  VALUE: SC-28.1
  ROLE: ConformsTo
- TYPE: Parent
  VALUE: V-222542
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-CRED-SESSION
STATUS: Active
TITLE: Session management: idle/absolute timeout, fixation, cookies
STATEMENT: >>>
Sessions use system-generated unique identifiers from an approved RNG and rotate on login (anti-fixation). Session IDs are never in URLs or otherwise exposed. Cookies are HttpOnly and Secure, sessions are validated server-side, and IDs are never reused. Idle and absolute timeouts are configurable (DoD preset: 15 minutes idle non-privileged, 10 minutes admin), as are concurrent-session limits. Timeout, sign-out, and account deletion destroy the session and its token family. Session create, renew, timeout, and destroy are audited.
<<<
COMMENT: >>>
KIND: requirement
BASE_UID: ARCH-CRED-SESSION
VERSION_N: 0
rbac_op: auth:session:manage
priority: 5
iteration: iter-r1
security.catalog_ref: AC-12
security.verification_note: AC-12 / AC-2(5) / AC-10 / SC-23(3); ASD V-222387 / V-222389 / V-222390 / V-222575 / V-222576 / V-222577 / V-222579 / V-222581 / V-222582 / V-222583.
edge: ← uses from FIX-DENY-SESSION-IDLE
edge: ← uses from ARCH-AUTH-LOCAL-BREAKGLASS
edge: ← uses from ARCH-AUTH-UPSTREAM-REVOKE
edge: ← satisfies from CAP-CRED-STORE
in_scope_of_contract: ReqALM product (build)
delivered_by_release: R1 platform follow-ups (deferred from foundation PR)
edge: → conforms_to to AC-12 (pin imprint=nist-800-53@rev5-dogfood-20261006)
edge: → conforms_to to AC-2.5 (pin imprint=nist-800-53@rev5-dogfood-20261006)
edge: → conforms_to to AC-10 (pin imprint=nist-800-53@rev5-dogfood-20261006)
edge: → conforms_to to SC-23 (pin imprint=nist-800-53@rev5-dogfood-20261006)
edge: → conforms_to to SC-23.3 (pin imprint=nist-800-53@rev5-dogfood-20261006)
edge: → conforms_to to V-222387 (pin imprint=asd-stig@v6r4)
edge: → conforms_to to V-222389 (pin imprint=asd-stig@v6r4)
edge: → conforms_to to V-222390 (pin imprint=asd-stig@v6r4)
edge: → conforms_to to V-222575 (pin imprint=asd-stig@v6r4)
edge: → conforms_to to V-222576 (pin imprint=asd-stig@v6r4)
edge: → conforms_to to V-222577 (pin imprint=asd-stig@v6r4)
edge: → conforms_to to V-222579 (pin imprint=asd-stig@v6r4)
edge: → conforms_to to V-222581 (pin imprint=asd-stig@v6r4)
edge: → conforms_to to V-222582 (pin imprint=asd-stig@v6r4)
edge: → conforms_to to V-222583 (pin imprint=asd-stig@v6r4)
<<<
RELATIONS:
- TYPE: Parent
  VALUE: ARCH-CRED
- TYPE: Parent
  VALUE: ARCH-CRED
  ROLE: Refines
- TYPE: Parent
  VALUE: A02
  ROLE: Refines
- TYPE: Parent
  VALUE: ARCH-UI-GUARD
  ROLE: Uses
- TYPE: Parent
  VALUE: AC-12
  ROLE: ConformsTo
- TYPE: Parent
  VALUE: AC-2.5
  ROLE: ConformsTo
- TYPE: Parent
  VALUE: AC-10
  ROLE: ConformsTo
- TYPE: Parent
  VALUE: SC-23
  ROLE: ConformsTo
- TYPE: Parent
  VALUE: SC-23.3
  ROLE: ConformsTo
- TYPE: Parent
  VALUE: V-222387
  ROLE: ConformsTo
- TYPE: Parent
  VALUE: V-222389
  ROLE: ConformsTo
- TYPE: Parent
  VALUE: V-222390
  ROLE: ConformsTo
- TYPE: Parent
  VALUE: V-222575
  ROLE: ConformsTo
- TYPE: Parent
  VALUE: V-222576
  ROLE: ConformsTo
- TYPE: Parent
  VALUE: V-222577
  ROLE: ConformsTo
- TYPE: Parent
  VALUE: V-222579
  ROLE: ConformsTo
- TYPE: Parent
  VALUE: V-222581
  ROLE: ConformsTo
- TYPE: Parent
  VALUE: V-222582
  ROLE: ConformsTo
- TYPE: Parent
  VALUE: V-222583
  ROLE: ConformsTo
- TYPE: Child
  VALUE: CONTRACT-ctr-reqalm-product
  ROLE: InScopeOf
- TYPE: Child
  VALUE: RELEASE-rel-r1-platform-followups
  ROLE: Delivers

[REQUIREMENT]
UID: ARCH-CRED-REAUTH
STATUS: Active
TITLE: Re-authentication (step-up) for sensitive actions
STATEMENT: >>>
Sensitive actions require recent authentication (step-up): line or tree approve (D12/D13), capability approve, ConformsTo pin apply/deny, gate sign-off, release ship, grant and role administration, client registration, and key operations. If auth_time is older than the configured max_age, or MFA is missing for a privileged slot, the action returns a step-up challenge and nothing is written.
<<<
COMMENT: >>>
KIND: requirement
BASE_UID: ARCH-CRED-REAUTH
VERSION_N: 0
rbac_op: auth:stepup
priority: 10
iteration: iter-r1
security.catalog_ref: IA-11
security.verification_note: IA-11 re-authentication; ASD V-222520.
edge: ← uses from FIX-DENY-STEPUP-STALE-AUTH
edge: ← uses from ARCH-AUTH-UPSTREAM-CONNECTOR
edge: ← satisfies from CAP-CRED-STORE
edge: ← uses from ARCH-FIGMA-AUTH
in_scope_of_contract: ReqALM product (build)
delivered_by_release: R1 platform follow-ups (deferred from foundation PR)
edge: → conforms_to to IA-11 (pin imprint=nist-800-53@rev5-dogfood-20261006)
edge: → conforms_to to V-222520 (pin imprint=asd-stig@v6r4)
<<<
RELATIONS:
- TYPE: Parent
  VALUE: ARCH-CRED
- TYPE: Parent
  VALUE: ARCH-CRED
  ROLE: Refines
- TYPE: Parent
  VALUE: D12
  ROLE: Refines
- TYPE: Parent
  VALUE: D13
  ROLE: Refines
- TYPE: Parent
  VALUE: ARCH-CAP-APPROVE
  ROLE: Refines
- TYPE: Parent
  VALUE: ARCH-GATE-SIGNOFF
  ROLE: Refines
- TYPE: Parent
  VALUE: G05
  ROLE: Refines
- TYPE: Parent
  VALUE: A07
  ROLE: Refines
- TYPE: Parent
  VALUE: IA-11
  ROLE: ConformsTo
- TYPE: Parent
  VALUE: V-222520
  ROLE: ConformsTo
- TYPE: Child
  VALUE: CONTRACT-ctr-reqalm-product
  ROLE: InScopeOf
- TYPE: Child
  VALUE: RELEASE-rel-r1-platform-followups
  ROLE: Delivers

[REQUIREMENT]
UID: ARCH-CRED-AUDIT
STATUS: Active
TITLE: Audit every authentication event
STATEMENT: >>>
Every authentication event is audited through the existing AuditLog pattern (ARCH-OTEL) with subject, client_id, source IP, user agent, outcome, and timestamp. Covered events: login success and failure, lockout and unlock, MFA result, step-up, token issue / refresh / rotation-reuse / revoke, client registration, session create / renew / timeout / destroy, account create / modify / disable / remove, and key operations. Secrets, tokens, and password material never appear in audit payloads.
<<<
COMMENT: >>>
KIND: requirement
BASE_UID: ARCH-CRED-AUDIT
VERSION_N: 0
priority: 5
iteration: iter-r1
security.catalog_ref: AU-2
security.verification_note: AU-2/3/12; ASD V-222462 / V-222441 / V-222442 / V-222443 / V-222445 / V-222467.
edge: ← uses from ARCH-AUTH-AS
edge: ← uses from ARCH-AUTH-LOCAL-BREAKGLASS
edge: ← refines from ARCH-AUTH-AGENT-ATTRIBUTION
edge: ← satisfies from CAP-AUTH-AUDIT
in_scope_of_contract: ReqALM product (build)
delivered_by_release: R1 — foundation shell + internal auth
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
edge: → conforms_to to V-222462 (pin imprint=asd-stig@v6r4)
edge: → conforms_to to V-222441 (pin imprint=asd-stig@v6r4)
edge: → conforms_to to V-222442 (pin imprint=asd-stig@v6r4)
edge: → conforms_to to V-222443 (pin imprint=asd-stig@v6r4)
edge: → conforms_to to V-222445 (pin imprint=asd-stig@v6r4)
edge: → conforms_to to V-222467 (pin imprint=asd-stig@v6r4)
<<<
RELATIONS:
- TYPE: Parent
  VALUE: ARCH-CRED
- TYPE: Parent
  VALUE: ARCH-CRED
  ROLE: Refines
- TYPE: Parent
  VALUE: ARCH-OTEL
  ROLE: Refines
- TYPE: Parent
  VALUE: AU-2
  ROLE: ConformsTo
- TYPE: Parent
  VALUE: AU-3
  ROLE: ConformsTo
- TYPE: Parent
  VALUE: AU-12
  ROLE: ConformsTo
- TYPE: Parent
  VALUE: V-222462
  ROLE: ConformsTo
- TYPE: Parent
  VALUE: V-222441
  ROLE: ConformsTo
- TYPE: Parent
  VALUE: V-222442
  ROLE: ConformsTo
- TYPE: Parent
  VALUE: V-222443
  ROLE: ConformsTo
- TYPE: Parent
  VALUE: V-222445
  ROLE: ConformsTo
- TYPE: Parent
  VALUE: V-222467
  ROLE: ConformsTo
- TYPE: Child
  VALUE: CONTRACT-ctr-reqalm-product
  ROLE: InScopeOf
- TYPE: Child
  VALUE: RELEASE-rel-r1-foundation-shell-auth
  ROLE: Delivers

[[/SECTION]]

[REQUIREMENT]
UID: ARCH-KEY
STATUS: Active
TITLE: Key / secret store — envelope encryption root of trust
STATEMENT: >>>
ReqAML's encryption root of trust is an external key / secret store using envelope encryption. A key-encryption key (KEK) is held outside the application database by the KeyProvider and wraps data-encryption keys (DEKs). DEKs are persisted only in wrapped form. Plaintext key material exists only in process memory, is never written to the database, logs, or source, and is zeroized when no longer needed.
<<<
COMMENT: >>>
KIND: requirement
BASE_UID: ARCH-KEY
VERSION_N: 0
priority: 5
iteration: iter-r1
security.catalog_ref: SC-12
security.verification_note: SC-12 key establishment/management; SC-28(3) cryptographic keys at rest.
edge: ← refines from ARCH-KEY-PROVIDER
edge: ← refines from ARCH-KEY-JWKS
edge: ← refines from ARCH-KEY-LIFECYCLE
edge: ← refines from ARCH-KEY-CUSTODIAN
edge: ← refines from ARCH-KEY-BREAKGLASS
edge: ← refines from ARCH-KEY-FIPS
edge: ← refines from ARCH-KEY-FAILCLOSED
edge: ← uses from ARCH-DEPLOY-PERIPHERALS
edge: ← uses from ARCH-BUILD-FOUNDATION
edge: ← uses from FIX-ALLOW-CRED-HASH-ONLY
edge: ← satisfies from CAP-KEY-ENVELOPE
edge: ← refines from ARCH-KEY-SCOPE
edge: ← refines from ARCH-KEY-SCOPE.1
in_scope_of_contract: ReqALM product (build)
delivered_by_release: R1 — foundation shell + internal auth
edge: → conforms_to to SC-12 (pin imprint=nist-800-53@rev5-dogfood-20261006)
edge: → conforms_to to SC-28 (pin imprint=nist-800-53@rev5-dogfood-20261006)
edge: → conforms_to to SC-28.1 (pin imprint=nist-800-53@rev5-dogfood-20261006)
edge: → conforms_to to SC-28.3 (pin imprint=nist-800-53@rev5-dogfood-20261006)
<<<
RELATIONS:
- TYPE: Parent
  VALUE: SEC-SEC
- TYPE: Parent
  VALUE: ARCH-DEVENV-SECRETS
  ROLE: Refines
- TYPE: Parent
  VALUE: SC-12
  ROLE: ConformsTo
- TYPE: Parent
  VALUE: SC-28
  ROLE: ConformsTo
- TYPE: Parent
  VALUE: SC-28.1
  ROLE: ConformsTo
- TYPE: Parent
  VALUE: SC-28.3
  ROLE: ConformsTo
- TYPE: Child
  VALUE: CONTRACT-ctr-reqalm-product
  ROLE: InScopeOf
- TYPE: Child
  VALUE: RELEASE-rel-r1-foundation-shell-auth
  ROLE: Delivers

[[SECTION]]
UID: ARCH-KEY-CHILDREN
TITLE: Children of ARCH-KEY

[REQUIREMENT]
UID: ARCH-KEY-PROVIDER
STATUS: Active
TITLE: Pluggable KeyProvider; OpenBao Transit default
STATEMENT: >>>
Key operations go through a pluggable KeyProvider abstraction: wrap/unwrap DEK, re-wrap, generate, rotate, revoke/disable, destroy, and sign with non-exportable signing keys. The default backend is OpenBao with the Transit engine (envelope encrypt/decrypt/rewrap plus sign) for dev, and it is suitable for production. The same interface also accepts a cloud KMS or an HSM over PKCS#11 (SoftHSM2 is used only to test the PKCS#11 path). HashiCorp Vault (BUSL) and LocalStack KMS are not defaults. Access to the KeyProvider is authenticated with deployment credentials injected at runtime, never committed (ARCH-DEVENV-SECRETS).
<<<
COMMENT: >>>
KIND: requirement
BASE_UID: ARCH-KEY-PROVIDER
VERSION_N: 0
priority: 5
iteration: iter-r1
security.catalog_ref: IA-7
security.verification_note: IA-7 cryptographic module authentication; ASD V-222555.
edge: ← uses from ARCH-KEY-JWKS
edge: ← refines from ARCH-DEVENV-KEYS
edge: ← satisfies from CAP-DEVENV-OPENBAO-BOOTSTRAP
edge: ← satisfies from CAP-KEY-ENVELOPE
edge: ← satisfies from CAP-TEST-MEMORY-KEYPROVIDER
edge: ← satisfies from CAP-TEST-PROD-BUILD-EXCLUDE
edge: ← uses from ARCH-ATTACH-ENCRYPT
edge: ← uses from ARCH-FIGMA-AUTH
edge: ← uses from ARCH-ATTACH-ENCRYPT.1
in_scope_of_contract: ReqALM product (build)
delivered_by_release: R1 — foundation shell + internal auth
edge: → conforms_to to IA-7 (pin imprint=nist-800-53@rev5-dogfood-20261006)
edge: → conforms_to to SC-12 (pin imprint=nist-800-53@rev5-dogfood-20261006)
edge: → conforms_to to V-222555 (pin imprint=asd-stig@v6r4)
<<<
RELATIONS:
- TYPE: Parent
  VALUE: ARCH-KEY
- TYPE: Parent
  VALUE: ARCH-KEY
  ROLE: Refines
- TYPE: Parent
  VALUE: ARCH-DEVENV-SECRETS
  ROLE: Uses
- TYPE: Parent
  VALUE: IA-7
  ROLE: ConformsTo
- TYPE: Parent
  VALUE: SC-12
  ROLE: ConformsTo
- TYPE: Parent
  VALUE: V-222555
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-KEY-SCOPE.1
STATUS: Draft
TITLE: What the key store protects (signing keys, secrets, sensitive fields)
STATEMENT: >>>
The key store protects: (1) OAuth token signing keys (ARCH-KEY-JWKS); (2) secrets the app must use (DB credentials, SMTP credentials, Azure DevOps connector tokens, upstream IdP client secrets, OTEL sink credentials, MFA secrets, object-store credentials, and outbound integration OAuth access and refresh tokens such as Figma), encrypted under DEKs; (3) peppers or HMAC keys used to hash server-side tokens (ARCH-CRED-TOKENS); (4) per-object data encryption keys for file attachments (ARCH-ATTACH-ENCRYPT), each wrapped by the KeyProvider KEK and stored beside the attachment metadata. Verify-only credentials are hashed, not encrypted. Field-level encryption applies only to columns that hold such secrets. Requirement content is not field-encrypted and relies on storage-level encryption at rest per deployment.
<<<
COMMENT: >>>
KIND: requirement
BASE_UID: ARCH-KEY-SCOPE
VERSION_N: 1
priority: 10
iteration: iter-r1
security.catalog_ref: SC-28.1
security.verification_note: Cyber 2026-10-09 attachments-figma mapping; content mint .1 (statement adds attachment DEKs, object-store creds, outbound integration OAuth tokens); v0 is delivered by shipped rel-r1-foundation-shell-auth and in ctr-reqalm-product, so v0 is never edited; v0 becomes superseded only when .1 is activated (D04).
edge: ← refines from ARCH-ATTACH-ENCRYPT
edge: ← refines from ARCH-FIGMA-AUTH
edge: ← refines from ARCH-ATTACH-ENCRYPT.1
edge: → conforms_to to SC-28.1 (pin imprint=nist-800-53@rev5-dogfood-20261006)
edge: → conforms_to to V-222588 (pin imprint=asd-stig@v6r4)
edge: → conforms_to to V-222589 (pin imprint=asd-stig@v6r4)
edge: → conforms_to to V-222642 (pin imprint=asd-stig@v6r4)
<<<
RELATIONS:
- TYPE: Parent
  VALUE: ARCH-KEY
- TYPE: Parent
  VALUE: ARCH-KEY
  ROLE: Refines
- TYPE: Parent
  VALUE: M03
  ROLE: Uses
- TYPE: Parent
  VALUE: SC-28.1
  ROLE: ConformsTo
- TYPE: Parent
  VALUE: V-222588
  ROLE: ConformsTo
- TYPE: Parent
  VALUE: V-222589
  ROLE: ConformsTo
- TYPE: Parent
  VALUE: V-222642
  ROLE: ConformsTo

[REQUIREMENT]
UID: ARCH-KEY-SCOPE
STATUS: Active
TITLE: What the key store protects (signing keys, secrets, sensitive fields)
STATEMENT: >>>
The key store protects: (1) OAuth token signing keys (ARCH-KEY-JWKS); (2) secrets the app must use (DB credentials, SMTP credentials, Azure DevOps connector tokens, upstream IdP client secrets, OTEL sink credentials, MFA secrets), encrypted under DEKs; (3) peppers or HMAC keys used to hash server-side tokens (ARCH-CRED-TOKENS). Verify-only credentials are hashed, not encrypted. Field-level encryption applies only to columns that hold such secrets. Requirement content is not field-encrypted and relies on storage-level encryption at rest per deployment.
<<<
COMMENT: >>>
KIND: requirement
BASE_UID: ARCH-KEY-SCOPE
VERSION_N: 0
priority: 10
iteration: iter-r1
security.catalog_ref: SC-28.1
security.verification_note: SC-28(1) cryptographic protection at rest; ASD V-222588 / V-222589 / V-222642.
edge: ← uses from ARCH-CRED-MFA
edge: ← uses from ARCH-CRED-TOKENS
edge: ← uses from ARCH-AUTH-UPSTREAM-CONNECTOR
edge: ← satisfies from CAP-KEY-ENVELOPE
in_scope_of_contract: ReqALM product (build)
delivered_by_release: R1 — foundation shell + internal auth
edge: → conforms_to to SC-28.1 (pin imprint=nist-800-53@rev5-dogfood-20261006)
edge: → conforms_to to V-222588 (pin imprint=asd-stig@v6r4)
edge: → conforms_to to V-222589 (pin imprint=asd-stig@v6r4)
edge: → conforms_to to V-222642 (pin imprint=asd-stig@v6r4)
<<<
RELATIONS:
- TYPE: Parent
  VALUE: ARCH-KEY
- TYPE: Parent
  VALUE: ARCH-KEY
  ROLE: Refines
- TYPE: Parent
  VALUE: M03
  ROLE: Uses
- TYPE: Parent
  VALUE: SC-28.1
  ROLE: ConformsTo
- TYPE: Parent
  VALUE: V-222588
  ROLE: ConformsTo
- TYPE: Parent
  VALUE: V-222589
  ROLE: ConformsTo
- TYPE: Parent
  VALUE: V-222642
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-KEY-JWKS
STATUS: Active
TITLE: Token signing keys: kid, JWKS, rotation with overlap window
STATEMENT: >>>
Each token signing key has a kid. By default it is a non-exportable OpenBao Transit key, so signing happens inside the KeyProvider and the kid is the key name plus version. The AS publishes public keys at its jwks_uri for the active key and any retired keys still inside the overlap window. Rotation is scheduled and on demand: a new key version starts signing, the prior version stays verify-only until the overlap window passes (at least the maximum access-token lifetime plus clock skew), and is then removed. After that, tokens with the retired kid are rejected.
<<<
COMMENT: >>>
KIND: requirement
BASE_UID: ARCH-KEY-JWKS
VERSION_N: 0
rbac_op: key:signing:rotate
priority: 5
iteration: iter-r1
security.catalog_ref: SC-12.3
security.verification_note: SC-12(3) asymmetric keys; SC-13; ASD V-222570.
edge: ← uses from ARCH-AUTH-AS
edge: ← uses from FIX-JWKS-ROTATION-OVERLAP
edge: ← satisfies from CAP-KEY-ENVELOPE
in_scope_of_contract: ReqALM product (build)
delivered_by_release: R1 — foundation shell + internal auth
edge: → conforms_to to SC-12.3 (pin imprint=nist-800-53@rev5-dogfood-20261006)
edge: → conforms_to to SC-13 (pin imprint=nist-800-53@rev5-dogfood-20261006)
edge: → conforms_to to V-222570 (pin imprint=asd-stig@v6r4)
<<<
RELATIONS:
- TYPE: Parent
  VALUE: ARCH-KEY
- TYPE: Parent
  VALUE: ARCH-KEY
  ROLE: Refines
- TYPE: Parent
  VALUE: ARCH-KEY-PROVIDER
  ROLE: Uses
- TYPE: Parent
  VALUE: SC-12.3
  ROLE: ConformsTo
- TYPE: Parent
  VALUE: SC-13
  ROLE: ConformsTo
- TYPE: Parent
  VALUE: V-222570
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-KEY-LIFECYCLE
STATUS: Active
TITLE: Key lifecycle: generate, rotate, revoke, destroy, online re-wrap
STATEMENT: >>>
Key lifecycle operations are generate, rotate (scheduled and on demand), revoke/disable, and destroy, for KEKs and DEKs. KEK rotation creates a new key version and re-wraps every DEK online (Transit rewrap, so plaintext is never exposed). Prior versions still unwrap until re-wrap finishes and is verified, then the minimum decryption version is raised to disable them. Reads and writes continue throughout with no downtime. Destroy is irreversible, needs the Key custodian (ARCH-KEY-CUSTODIAN), and requires confirmation that no live ciphertext depends on the key. Every key operation emits an audit event through the AuditLog pattern (operation, key id/version, actor, outcome) and never includes key material.
<<<
COMMENT: >>>
KIND: requirement
BASE_UID: ARCH-KEY-LIFECYCLE
VERSION_N: 0
rbac_op: key:kek:rotate, key:dek:rewrap, key:revoke, key:destroy
priority: 5
iteration: iter-r1
security.catalog_ref: SC-12
security.verification_note: SC-12 / SC-12(2) / SC-12(3); AU-2.
edge: ← uses from FIX-ALLOW-KEK-REWRAP-ONLINE
edge: ← satisfies from CAP-KEY-ENVELOPE
edge: ← refines from ARCH-KEY-RUNTIME-CACHE
in_scope_of_contract: ReqALM product (build)
delivered_by_release: R1 — foundation shell + internal auth
edge: → conforms_to to SC-12 (pin imprint=nist-800-53@rev5-dogfood-20261006)
edge: → conforms_to to SC-12.2 (pin imprint=nist-800-53@rev5-dogfood-20261006)
edge: → conforms_to to SC-12.3 (pin imprint=nist-800-53@rev5-dogfood-20261006)
edge: → conforms_to to AU-2 (pin imprint=nist-800-53@rev5-dogfood-20261006)
<<<
RELATIONS:
- TYPE: Parent
  VALUE: ARCH-KEY
- TYPE: Parent
  VALUE: ARCH-KEY
  ROLE: Refines
- TYPE: Parent
  VALUE: ARCH-KEY-CUSTODIAN
  ROLE: Uses
- TYPE: Parent
  VALUE: ARCH-OTEL
  ROLE: Uses
- TYPE: Parent
  VALUE: SC-12
  ROLE: ConformsTo
- TYPE: Parent
  VALUE: SC-12.2
  ROLE: ConformsTo
- TYPE: Parent
  VALUE: SC-12.3
  ROLE: ConformsTo
- TYPE: Parent
  VALUE: AU-2
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-KEY-CUSTODIAN
STATUS: Active
TITLE: Key custodian role (separation of duties)
STATEMENT: >>>
Key operations (KEK/DEK rotate, revoke, destroy, provider reconfigure, recovery) need the deployment-scoped Key custodian role. No existing role fits: project and client roles are tenant-scoped, and the permission tree has no ops or deployment role ('No separate Deployer in v1'). For separation of duties, the Key custodian is distinct from Client admin and Project admin, and holding both on one deployment is refused unless a documented exception is approved. The role grants no access to requirement content. Scheduled automatic rotation runs as an audited system principal.
<<<
COMMENT: >>>
KIND: requirement
BASE_UID: ARCH-KEY-CUSTODIAN
VERSION_N: 0
rbac_op: key:*
priority: 10
iteration: iter-r1
security.catalog_ref: AC-5
security.verification_note: AC-5 separation of duties; AC-6 least privilege.
edge: ← uses from ARCH-KEY-LIFECYCLE
edge: ← uses from ARCH-KEY-BREAKGLASS
edge: ← uses from FIX-DENY-KEYOP-NO-CUSTODIAN
in_scope_of_contract: ReqALM product (build)
delivered_by_release: R1 platform follow-ups (deferred from foundation PR)
edge: → conforms_to to AC-5 (pin imprint=nist-800-53@rev5-dogfood-20261006)
edge: → conforms_to to AC-6 (pin imprint=nist-800-53@rev5-dogfood-20261006)
<<<
RELATIONS:
- TYPE: Parent
  VALUE: ARCH-KEY
- TYPE: Parent
  VALUE: ARCH-KEY
  ROLE: Refines
- TYPE: Parent
  VALUE: ARCH-API-RBAC
  ROLE: Uses
- TYPE: Parent
  VALUE: ARCH-CRED-MFA
  ROLE: Uses
- TYPE: Parent
  VALUE: AC-5
  ROLE: ConformsTo
- TYPE: Parent
  VALUE: AC-6
  ROLE: ConformsTo
- TYPE: Child
  VALUE: CONTRACT-ctr-reqalm-product
  ROLE: InScopeOf
- TYPE: Child
  VALUE: RELEASE-rel-r1-platform-followups
  ROLE: Delivers

[REQUIREMENT]
UID: ARCH-KEY-BREAKGLASS
STATUS: Active
TITLE: Key recovery / break-glass procedure
STATEMENT: >>>
A documented key recovery / break-glass procedure covers KEK or KeyProvider loss and custodian unavailability. It uses OpenBao unseal/recovery shares or provider-native recovery held under split knowledge and dual control (M-of-N custodians), restores without exposing plaintext keys, and rotates keys afterward. Every break-glass use is audited and reviewed, and a restore exercise runs on a schedule.
<<<
COMMENT: >>>
KIND: requirement
BASE_UID: ARCH-KEY-BREAKGLASS
VERSION_N: 0
rbac_op: key:recover
priority: 15
iteration: iter-r1
security.catalog_ref: SC-12.1
security.verification_note: SC-12(1) key availability; AC-5 dual control.
edge: ← uses from ARCH-AUTH-LOCAL-BREAKGLASS
in_scope_of_contract: ReqALM product (build)
delivered_by_release: R1 platform follow-ups (deferred from foundation PR)
edge: → conforms_to to SC-12.1 (pin imprint=nist-800-53@rev5-dogfood-20261006)
edge: → conforms_to to AC-5 (pin imprint=nist-800-53@rev5-dogfood-20261006)
<<<
RELATIONS:
- TYPE: Parent
  VALUE: ARCH-KEY
- TYPE: Parent
  VALUE: ARCH-KEY
  ROLE: Refines
- TYPE: Parent
  VALUE: ARCH-KEY-CUSTODIAN
  ROLE: Uses
- TYPE: Parent
  VALUE: SC-12.1
  ROLE: ConformsTo
- TYPE: Parent
  VALUE: AC-5
  ROLE: ConformsTo
- TYPE: Child
  VALUE: CONTRACT-ctr-reqalm-product
  ROLE: InScopeOf
- TYPE: Child
  VALUE: RELEASE-rel-r1-platform-followups
  ROLE: Delivers

[REQUIREMENT]
UID: ARCH-KEY-FIPS
STATUS: Active
TITLE: FIPS-validated cryptographic modules where applicable
STATEMENT: >>>
Where a deployment requires it (DoD/federal profile), all cryptographic operations (hashing, signing, encryption, key wrap, and RNG for session IDs and tokens) use FIPS 140-validated modules (FIPS mode). Password hashing then uses PBKDF2 (ARCH-CRED-HASH), and a KeyProvider build that is not FIPS-validated is refused in that mode. Whether FIPS mode is the default for commercial deployments is an open question.
<<<
COMMENT: >>>
KIND: requirement
BASE_UID: ARCH-KEY-FIPS
VERSION_N: 0
priority: 10
iteration: iter-r1
security.catalog_ref: SC-13
security.verification_note: SC-13 cryptographic protection; ASD V-222570 / V-222571 / V-222572 / V-222583.
edge: ← uses from ARCH-CRED-HASH
edge: ← uses from ARCH-AUTH-PROFILE
in_scope_of_contract: ReqALM product (build)
delivered_by_release: R1 platform follow-ups (deferred from foundation PR)
edge: → conforms_to to SC-13 (pin imprint=nist-800-53@rev5-dogfood-20261006)
edge: → conforms_to to V-222570 (pin imprint=asd-stig@v6r4)
edge: → conforms_to to V-222571 (pin imprint=asd-stig@v6r4)
edge: → conforms_to to V-222572 (pin imprint=asd-stig@v6r4)
edge: → conforms_to to V-222583 (pin imprint=asd-stig@v6r4)
<<<
RELATIONS:
- TYPE: Parent
  VALUE: ARCH-KEY
- TYPE: Parent
  VALUE: ARCH-KEY
  ROLE: Refines
- TYPE: Parent
  VALUE: SC-13
  ROLE: ConformsTo
- TYPE: Parent
  VALUE: V-222570
  ROLE: ConformsTo
- TYPE: Parent
  VALUE: V-222571
  ROLE: ConformsTo
- TYPE: Parent
  VALUE: V-222572
  ROLE: ConformsTo
- TYPE: Parent
  VALUE: V-222583
  ROLE: ConformsTo
- TYPE: Child
  VALUE: CONTRACT-ctr-reqalm-product
  ROLE: InScopeOf
- TYPE: Child
  VALUE: RELEASE-rel-r1-platform-followups
  ROLE: Delivers

[REQUIREMENT]
UID: ARCH-KEY-FAILCLOSED
STATUS: Active
TITLE: Fail closed when the KEK / KeyProvider is unavailable
STATEMENT: >>>
In production, ReqAML fails closed when the KEK or KeyProvider is unreachable or sealed. The app does not start or reports not ready (ARCH-DEVENV-HEALTH / M04), and it refuses operations that need key material. It never falls back to plaintext, cached plaintext KEKs on disk, or a dev provider. Unavailability is audited and alerted.
<<<
COMMENT: >>>
KIND: requirement
BASE_UID: ARCH-KEY-FAILCLOSED
VERSION_N: 0
priority: 5
iteration: iter-r1
security.catalog_ref: SC-24
security.verification_note: SC-24 fail in known state; SC-12(1).
edge: ← uses from FIX-DENY-KEK-UNREACHABLE-PROD
edge: ← satisfies from CAP-READY-PROBES
edge: ← satisfies from CAP-KEY-ENVELOPE
edge: ← uses from ARCH-ATTACH-ENCRYPT
edge: ← uses from ARCH-ATTACH-ENCRYPT.1
in_scope_of_contract: ReqALM product (build)
delivered_by_release: R1 — foundation shell + internal auth
edge: → conforms_to to SC-24 (pin imprint=nist-800-53@rev5-dogfood-20261006)
edge: → conforms_to to SC-12.1 (pin imprint=nist-800-53@rev5-dogfood-20261006)
<<<
RELATIONS:
- TYPE: Parent
  VALUE: ARCH-KEY
- TYPE: Parent
  VALUE: ARCH-KEY
  ROLE: Refines
- TYPE: Parent
  VALUE: ARCH-DEVENV-HEALTH
  ROLE: Uses
- TYPE: Parent
  VALUE: M04
  ROLE: Uses
- TYPE: Parent
  VALUE: SC-24
  ROLE: ConformsTo
- TYPE: Parent
  VALUE: SC-12.1
  ROLE: ConformsTo
- TYPE: Child
  VALUE: CONTRACT-ctr-reqalm-product
  ROLE: InScopeOf
- TYPE: Child
  VALUE: RELEASE-rel-r1-foundation-shell-auth
  ROLE: Delivers

[REQUIREMENT]
UID: ARCH-KEY-RUNTIME-CACHE
STATUS: Active
TITLE: Signing key cache and span flush on shutdown
STATEMENT: >>>
The runtime shall cache the unwrapped signing key in-process for performance, shall clear that cache on key rotation events, and shall flush OpenTelemetry spans on graceful shutdown after draining in-flight token operations.
<<<
COMMENT: >>>
KIND: requirement
BASE_UID: ARCH-KEY-RUNTIME-CACHE
VERSION_N: 0
priority: 15
iteration: iter-r1
security.catalog_ref: SC-12
security.verification_note: Groomed 2026-10-09; pre-write or UI track.
in_scope_of_contract: ReqALM product (build)
<<<
RELATIONS:
- TYPE: Parent
  VALUE: ARCH-KEY
- TYPE: Parent
  VALUE: ARCH-KEY-LIFECYCLE
  ROLE: Refines
- TYPE: Child
  VALUE: CONTRACT-ctr-reqalm-product
  ROLE: InScopeOf

[[/SECTION]]

[REQUIREMENT]
UID: CAP-CRED-STORE
STATUS: Active
TITLE: Credential store: Argon2id, lockout, MFA, hashed tokens
STATEMENT: >>>
Local credentials use Argon2id password hashes (legacy dev SHA-256 re-hashed on login), throttling/lockout after repeated failures, TOTP MFA for privileged roles (wrapped MFA secrets via KeyProvider), server-side refresh token hashes, and lockout audit events. Acceptance: auth-flow-smoke lockout bed; privileged MFA login (sam-security) after `pnpm devenv:mfa` or first-login enrollment.
<<<
COMMENT: >>>
KIND: capability
BASE_UID: CAP-CRED-STORE
VERSION_N: 0
priority: 10
iteration: iter-r1
security.catalog_ref: IA-5
security.verification_note: IA-5 / AC-7 credential controls. Verified: Local Docker 2026-10-07 on PR #13 follow-up (6a5f0db + verification fixes), fresh volumes: `pnpm devenv:init` idempotent (byte-identical rerun), `--rotate` issues new secrets (needs `down -v` for the Postgres volume), secrets files mode 600 and gitignored; `docker compose up --build -d --wait` with and without the hostports overlay (app 127.0.0.1:3000 only; peripherals unpublished without the overlay, loopback-only with it); /ready all green, restart count 0; `pnpm devenv:smoke` pass incl. auth-flow-smoke (server-side OAuth handoffs, PKCE S256, refresh rotation/reuse family revoke, RFC7009 refresh+access revoke, lockout + username normalize, Reader RBAC 403, wrong audience 401 at MCP, upstream connectors 401 unauthenticated, session cookie HttpOnly+SameSite=Lax, cookie mutation without CSRF 401, signout ends session, sam-security MFA login via `devenv:mfa`, TOTP replay rejected (and one wrong code does not lock the account), agent tokens default Reader / Author max / Developer+ refused, TTL <= 1h, agent token revoked 401), auth_audit_events incl. agent-attributed mutation, IP throttle 200 -> 401 after 20 failures, production refused dev accounts/keys, missing REQALM_ISSUER_URL and blanket trustProxy; headless Chrome first-login TOTP enrollment (jamie-ao) then MFA re-login; `@reqalm/app` test 30/30, typecheck pass; seed yaml_to_strictdoc --validate pass; TOTP secrets envelope-wrapped; replay of the same code within its window rejected.
in_scope_of_contract: ReqALM product (build)
delivered_by_release: R1 — foundation shell + internal auth
edge: → conforms_to to IA-5 (pin imprint=nist-800-53@rev5-dogfood-20261006)
<<<
RELATIONS:
- TYPE: Parent
  VALUE: SEC-SEC
- TYPE: Parent
  VALUE: ARCH-AUTH-LOCAL.1
  ROLE: Satisfies
- TYPE: Parent
  VALUE: ARCH-CRED
  ROLE: Satisfies
- TYPE: Parent
  VALUE: ARCH-CRED-HASH
  ROLE: Satisfies
- TYPE: Parent
  VALUE: ARCH-CRED-POLICY
  ROLE: Satisfies
- TYPE: Parent
  VALUE: ARCH-CRED-LOCKOUT
  ROLE: Satisfies
- TYPE: Parent
  VALUE: ARCH-CRED-MFA
  ROLE: Satisfies
- TYPE: Parent
  VALUE: ARCH-CRED-TOKENS
  ROLE: Satisfies
- TYPE: Parent
  VALUE: ARCH-CRED-SESSION
  ROLE: Satisfies
- TYPE: Parent
  VALUE: ARCH-CRED-REAUTH
  ROLE: Satisfies
- TYPE: Parent
  VALUE: IA-5
  ROLE: ConformsTo
- TYPE: Child
  VALUE: CONTRACT-ctr-reqalm-product
  ROLE: InScopeOf
- TYPE: Child
  VALUE: RELEASE-rel-r1-foundation-shell-auth
  ROLE: Delivers

[REQUIREMENT]
UID: CAP-KEY-ENVELOPE
STATUS: Active
TITLE: KeyProvider envelope encryption and JWKS signing keys
STATEMENT: >>>
OpenBao Transit wraps signing private keys and MFA secrets (envelope encryption). ES256 signing keys are published at `/oauth/jwks` with rotation support (retired keys remain during overlap window). Production startup fails closed when dev-marked OpenBao is configured (existing prod self-check). Acceptance: JWKS endpoint serves active keys; token issue uses KeyProvider-wrapped private key. Production follow-up: FIPS-validated modules and OpenBao Transit-sign (signing in HSM) — R1 uses Transit-wrapped extractable ES256 private keys in the app process.
<<<
COMMENT: >>>
KIND: capability
BASE_UID: CAP-KEY-ENVELOPE
VERSION_N: 0
priority: 10
iteration: iter-r1
security.catalog_ref: SC-12
security.verification_note: SC-12 / SC-28(3). Verified: Local Docker 2026-10-07 on PR #13 follow-up (6a5f0db + verification fixes), fresh volumes: `pnpm devenv:init` idempotent (byte-identical rerun), `--rotate` issues new secrets (needs `down -v` for the Postgres volume), secrets files mode 600 and gitignored; `docker compose up --build -d --wait` with and without the hostports overlay (app 127.0.0.1:3000 only; peripherals unpublished without the overlay, loopback-only with it); /ready all green, restart count 0; `pnpm devenv:smoke` pass incl. auth-flow-smoke (server-side OAuth handoffs, PKCE S256, refresh rotation/reuse family revoke, RFC7009 refresh+access revoke, lockout + username normalize, Reader RBAC 403, wrong audience 401 at MCP, upstream connectors 401 unauthenticated, session cookie HttpOnly+SameSite=Lax, cookie mutation without CSRF 401, signout ends session, sam-security MFA login via `devenv:mfa`, TOTP replay rejected (and one wrong code does not lock the account), agent tokens default Reader / Author max / Developer+ refused, TTL <= 1h, agent token revoked 401), auth_audit_events incl. agent-attributed mutation, IP throttle 200 -> 401 after 20 failures, production refused dev accounts/keys, missing REQALM_ISSUER_URL and blanket trustProxy; headless Chrome first-login TOTP enrollment (jamie-ao) then MFA re-login; `@reqalm/app` test 30/30, typecheck pass; seed yaml_to_strictdoc --validate pass; `/oauth/jwks` serves Transit-wrapped ES256. FIPS/Transit-sign deferred.
in_scope_of_contract: ReqALM product (build)
delivered_by_release: R1 — foundation shell + internal auth
edge: → conforms_to to SC-12 (pin imprint=nist-800-53@rev5-dogfood-20261006)
<<<
RELATIONS:
- TYPE: Parent
  VALUE: SEC-SEC
- TYPE: Parent
  VALUE: ARCH-KEY
  ROLE: Satisfies
- TYPE: Parent
  VALUE: ARCH-KEY-PROVIDER
  ROLE: Satisfies
- TYPE: Parent
  VALUE: ARCH-KEY-SCOPE
  ROLE: Satisfies
- TYPE: Parent
  VALUE: ARCH-KEY-JWKS
  ROLE: Satisfies
- TYPE: Parent
  VALUE: ARCH-KEY-LIFECYCLE
  ROLE: Satisfies
- TYPE: Parent
  VALUE: ARCH-KEY-FAILCLOSED
  ROLE: Satisfies
- TYPE: Parent
  VALUE: SC-12
  ROLE: ConformsTo
- TYPE: Child
  VALUE: CONTRACT-ctr-reqalm-product
  ROLE: InScopeOf
- TYPE: Child
  VALUE: RELEASE-rel-r1-foundation-shell-auth
  ROLE: Delivers

[REQUIREMENT]
UID: CAP-TEST-MEMORY-KEYPROVIDER
STATUS: Active
TITLE: In-memory KeyProvider fake for tests
STATEMENT: >>>
Tests inject `createMemoryKeyProvider()` implementing the production KeyProvider interface (wrapSecret/unwrapSecret/ensureReady) without OpenBao. Production wiring still uses OpenBao Transit.
<<<
COMMENT: >>>
KIND: capability
BASE_UID: CAP-TEST-MEMORY-KEYPROVIDER
VERSION_N: 0
priority: 10
iteration: iter-r1
security.catalog_ref: SC-12
security.verification_note: Dev/test only; no production path change.
in_scope_of_contract: ReqALM product (build)
delivered_by_release: R1 — in-process test harness (no Docker)
<<<
RELATIONS:
- TYPE: Parent
  VALUE: SEC-SEC
- TYPE: Parent
  VALUE: ARCH-KEY-PROVIDER
  ROLE: Satisfies
- TYPE: Child
  VALUE: CONTRACT-ctr-reqalm-product
  ROLE: InScopeOf
- TYPE: Child
  VALUE: RELEASE-rel-r1-test-harness
  ROLE: Delivers

[REQUIREMENT]
UID: ARCH-SEC-HEADERS
STATUS: Active
TITLE: Security headers before wide bind
STATEMENT: >>>
Before any non-127.0.0.1 deployment, HTTP responses shall send security headers including Content-Security-Policy default-src 'self', frame-ancestors 'none', X-Content-Type-Options nosniff, and Referrer-Policy no-referrer. Request logs shall record the path only (no query strings with secrets).
<<<
COMMENT: >>>
KIND: requirement
BASE_UID: ARCH-SEC-HEADERS
VERSION_N: 0
priority: 15
iteration: iter-r1
security.catalog_ref: SC-8
security.verification_note: Groomed 2026-10-09; pre-write or UI track.
edge: ← refines from ARCH-ATTACH-SERVE
in_scope_of_contract: ReqALM product (build)
<<<
RELATIONS:
- TYPE: Parent
  VALUE: SEC-SEC
- TYPE: Parent
  VALUE: ARCH-API
  ROLE: Refines
- TYPE: Child
  VALUE: CONTRACT-ctr-reqalm-product
  ROLE: InScopeOf

[REQUIREMENT]
UID: SYS-CYBER-UPKEEP
STATUS: Draft
TITLE: Ongoing cyber upkeep (ReqALM operations)
STATEMENT: >>>
PLANNED system requirement (not shipped). ReqALM in production shall sustain ongoing cyber upkeep: continuous monitoring, vulnerability and flaw remediation, account lifecycle review, and audit log analysis — implemented by the draft CAP-UPKEEP-* capability pack and owned under maintenance contract ctr-reqalm-maintenance.
<<<
COMMENT: >>>
KIND: requirement
BASE_UID: SYS-CYBER-UPKEEP
VERSION_N: 0
priority: 40
iteration: iter-r1
security.catalog_ref: CA-7
security.verification_note: Planned system requirement — not shipped; satisfied by draft CAP-UPKEEP-* pack.
edge: ← satisfies from CAP-UPKEEP-MONTHLY-SEC-AUDIT
edge: ← satisfies from CAP-UPKEEP-MONTHLY-DEPS-VULN
edge: ← satisfies from CAP-UPKEEP-QUARTERLY-ACCESS-RECERT
edge: ← satisfies from CAP-UPKEEP-AUDIT-LOG-REVIEW
edge: → conforms_to to CA-7 (pin imprint=nist-800-53@rev5-dogfood-20261006)
edge: → conforms_to to RA-5 (pin imprint=nist-800-53@rev5-dogfood-20261006)
edge: → conforms_to to SI-2 (pin imprint=nist-800-53@rev5-dogfood-20261006)
edge: → conforms_to to AC-2 (pin imprint=nist-800-53@rev5-dogfood-20261006)
edge: → conforms_to to AU-6 (pin imprint=nist-800-53@rev5-dogfood-20261006)
<<<
RELATIONS:
- TYPE: Parent
  VALUE: SEC-SEC
- TYPE: Parent
  VALUE: CA-7
  ROLE: ConformsTo
- TYPE: Parent
  VALUE: RA-5
  ROLE: ConformsTo
- TYPE: Parent
  VALUE: SI-2
  ROLE: ConformsTo
- TYPE: Parent
  VALUE: AC-2
  ROLE: ConformsTo
- TYPE: Parent
  VALUE: AU-6
  ROLE: ConformsTo

[REQUIREMENT]
UID: ARCH-ATTACH
STATUS: Draft
TITLE: File attachments: parent levels, scope, lifecycle
STATEMENT: >>>
ReqALM stores file attachments (bytes in an object store, metadata in Postgres) on exactly one parent: a client, a project, a requirement version, a capability version, a release, a contract, or a catalog control within a project-owned catalog imprint. Attachments are never parented to trace edges, approval records, gate signoffs, change sets, audit events, or controls in a standard (shared) imprint; evidence for those is attached to the owning version, release, or contract and referenced by id. Every attachment row carries client_id and project_id (null only for client-level), and all reads and writes enforce ARCH-CP-SCOPE. Attachments are soft-deleted (deleted_at, deleted_by) and hidden from default lists; bytes are retained for auditors. Permanent wipe of a restricted or legally held attachment is a separate Client admin operation (attachment:wipe) that needs step-up re-authentication and writes an audit row; it never runs from the normal delete path.
<<<
COMMENT: >>>
KIND: requirement
BASE_UID: ARCH-ATTACH
VERSION_N: 0
rbac_op: attachment:read
priority: 10
iteration: iter-r1
security.catalog_ref: AC-3
security.verification_note: Cyber 2026-10-09 attachments-figma mapping; Umbrella. Valid parents: client, project, requirement version, capability version, release, contract, catalog control (project-owned imprint only). Not: trace edges, approvals/gate_signoffs, audit_events, change_sets.
edge: ← refines from ARCH-ATTACH-PIN-VERSION
edge: ← refines from ARCH-ATTACH-SCOPE
edge: ← refines from ARCH-ATTACH-ENCRYPT
edge: ← refines from ARCH-ATTACH-AUDIT
edge: ← refines from ARCH-ATTACH-SERVE
edge: ← refines from ARCH-ATTACH-UPLOAD
edge: ← refines from ARCH-ATTACH-SCAN
edge: ← satisfies from CAP-ATTACH-READ
edge: ← refines from ARCH-ATTACH-VERSIONS
edge: ← refines from ARCH-ATTACH-PIN-VERSION.1
edge: ← refines from ARCH-ATTACH-SCOPE.1
edge: ← refines from ARCH-ATTACH-ENCRYPT.1
edge: ← satisfies from CAP-SEED-ATTACH-FIGMA
in_scope_of_contract: ReqALM product (build)
edge: → conforms_to to AC-3 (pin imprint=nist-800-53@rev5-dogfood-20261006)
edge: → conforms_to to MP-6 (pin imprint=nist-800-53@rev5-dogfood-20261006)
edge: → conforms_to to SI-12 (pin imprint=nist-800-53@rev5-dogfood-20261006)
edge: → conforms_to to V-222425 (pin imprint=asd-stig@v6r4)
<<<
RELATIONS:
- TYPE: Parent
  VALUE: SEC-SEC
- TYPE: Parent
  VALUE: ARCH-CP-SCOPE
  ROLE: Refines
- TYPE: Parent
  VALUE: C05
  ROLE: Refines
- TYPE: Parent
  VALUE: AC-3
  ROLE: ConformsTo
- TYPE: Parent
  VALUE: MP-6
  ROLE: ConformsTo
- TYPE: Parent
  VALUE: SI-12
  ROLE: ConformsTo
- TYPE: Parent
  VALUE: V-222425
  ROLE: ConformsTo
- TYPE: Child
  VALUE: CONTRACT-ctr-reqalm-product
  ROLE: InScopeOf

[[SECTION]]
UID: ARCH-ATTACH-CHILDREN
TITLE: Children of ARCH-ATTACH

[REQUIREMENT]
UID: ARCH-ATTACH-PIN-VERSION
STATUS: Draft
TITLE: Attachments pin to the parent version, not the line
STATEMENT: >>>
An attachment on a requirement or capability binds to that exact version uid, never to the line. A new version (.N) starts with no attachments; the author may carry selected attachments forward explicitly, which creates new rows that reference the same content sha256 and record carried_from. Attachments on a shipped or locked version are append-only: they can be added (as later evidence) but not replaced or soft-deleted except by attachment:wipe. Adding or removing an attachment is not a content mint and does not change statement_hash, but it flags needs re-check on the version's verification. Clients, projects, releases, contracts, and catalog controls have no versions; attachments bind to them directly, and attachments on a shipped release or signed contract are append-only.
<<<
COMMENT: >>>
KIND: requirement
BASE_UID: ARCH-ATTACH-PIN-VERSION
VERSION_N: 0
rbac_op: attachment:read
priority: 10
iteration: iter-r1
security.catalog_ref: CM-3
security.verification_note: Cyber 2026-10-09 attachments-figma mapping; Version pinning matches the mint rule (ARCH-MINT-KIND, ARCH-LOCKED): evidence is immutable once shipped.
edge: ← satisfies from CAP-ATTACH-READ
edge: ← satisfies from CAP-ATTACH-WRITE
edge: ← satisfies from CAP-READ-ARTIFACTS
in_scope_of_contract: ReqALM product (build)
edge: → conforms_to to CM-3 (pin imprint=nist-800-53@rev5-dogfood-20261006)
edge: → conforms_to to AU-9 (pin imprint=nist-800-53@rev5-dogfood-20261006)
edge: → conforms_to to SI-7 (pin imprint=nist-800-53@rev5-dogfood-20261006)
<<<
RELATIONS:
- TYPE: Parent
  VALUE: ARCH-ATTACH
- TYPE: Parent
  VALUE: ARCH-ATTACH
  ROLE: Refines
- TYPE: Parent
  VALUE: ARCH-MINT-KIND
  ROLE: Refines
- TYPE: Parent
  VALUE: ARCH-LOCKED
  ROLE: Refines
- TYPE: Parent
  VALUE: ARCH-TRACE-RECHECK
  ROLE: Uses
- TYPE: Parent
  VALUE: CM-3
  ROLE: ConformsTo
- TYPE: Parent
  VALUE: AU-9
  ROLE: ConformsTo
- TYPE: Parent
  VALUE: SI-7
  ROLE: ConformsTo
- TYPE: Child
  VALUE: CONTRACT-ctr-reqalm-product
  ROLE: InScopeOf

[REQUIREMENT]
UID: ARCH-ATTACH-PIN-VERSION.1
STATUS: Draft
TITLE: Attachments pin to the parent version, not the line
STATEMENT: >>>
Parent requirement and capability versions pin a specific attachment version id, never an attachment line or a blob directly, so stepping through a parent's version history shows the exact file version each parent version pinned. A new parent version (.N) starts with no pins; carry-forward to it is explicit and links the same blob (ARCH-ATTACH-VERSIONS). Pins on a shipped or locked parent version, a shipped release, or a signed contract are immutable and append-only: pins can be added as later evidence, but not re-pinned, replaced, or soft-deleted except by attachment:wipe. On an unlocked parent, re-pinning to a newer attachment version is an explicit, audited action that flags needs re-check on the parent's verification. Pin changes are not content mints and do not change statement_hash. Download URLs always reference an attachment version id; only the list view may show the latest version by default, and it labels it as latest. Clients, projects, releases, contracts, and catalog controls have no versions; their pins bind to them directly under the same rules.
<<<
COMMENT: >>>
KIND: requirement
BASE_UID: ARCH-ATTACH-PIN-VERSION
VERSION_N: 1
rbac_op: attachment:read
priority: 10
iteration: iter-r1
security.catalog_ref: CM-3
security.verification_note: Cyber 2026-10-09 attachments delta v3; content mint: pins target attachment version ids; carry-forward by link.
edge: ← satisfies from CAP-ATTACH-READ
edge: ← satisfies from CAP-ATTACH-WRITE
edge: → conforms_to to CM-3 (pin imprint=nist-800-53@rev5-dogfood-20261006)
edge: → conforms_to to AU-9 (pin imprint=nist-800-53@rev5-dogfood-20261006)
edge: → conforms_to to SI-7 (pin imprint=nist-800-53@rev5-dogfood-20261006)
<<<
RELATIONS:
- TYPE: Parent
  VALUE: ARCH-ATTACH
- TYPE: Parent
  VALUE: ARCH-ATTACH
  ROLE: Refines
- TYPE: Parent
  VALUE: ARCH-MINT-KIND
  ROLE: Refines
- TYPE: Parent
  VALUE: ARCH-LOCKED
  ROLE: Refines
- TYPE: Parent
  VALUE: ARCH-TRACE-RECHECK
  ROLE: Uses
- TYPE: Parent
  VALUE: CM-3
  ROLE: ConformsTo
- TYPE: Parent
  VALUE: AU-9
  ROLE: ConformsTo
- TYPE: Parent
  VALUE: SI-7
  ROLE: ConformsTo
- TYPE: Parent
  VALUE: ARCH-ATTACH-VERSIONS
  ROLE: Uses

[REQUIREMENT]
UID: ARCH-ATTACH-SCOPE
STATUS: Draft
TITLE: Attachment read inherits parent scope, redaction, and id validation
STATEMENT: >>>
Access to an attachment follows its parent object's scope and role permissions at every parent level: listing or downloading requires the read permission of the parent as granted by the caller's role (client read for a client-level attachment, project read for a project, requirement:read for a requirement version, and so on), checked server-side on every request; creating or deleting requires the parent's write-level permission plus attachment:create. There is no attachment-specific grant model. If the caller cannot read the parent, or the parent or attachment is restricted for the caller, or the attachment is soft-deleted, the response is the same 404 as a nonexistent id, with no difference in body, headers, or timing class. Attachment ids are server-generated and must match the allowlist ^att_[0-9a-z]{26}$; any other value is rejected with 400 before any lookup, and the raw value is not logged (logs record a redacted placeholder). List responses return metadata only: id, sanitized display name, size in bytes, media type (as detected), sha256, scan state, uploaded_by identity_id, created_at. They never return storage keys, object-store URLs, or content.
<<<
COMMENT: >>>
KIND: requirement
BASE_UID: ARCH-ATTACH-SCOPE
VERSION_N: 0
rbac_op: attachment:read
priority: 5
iteration: iter-r1
security.catalog_ref: AC-3
security.verification_note: Cyber 2026-10-09 attachments-figma mapping; Same-404 rule as restricted relations (ARCH-SEC-REL-STUB, ARCH-SEC-XPROJ-READ).
edge: ← satisfies from CAP-ATTACH-READ
in_scope_of_contract: ReqALM product (build)
edge: → conforms_to to AC-3 (pin imprint=nist-800-53@rev5-dogfood-20261006)
edge: → conforms_to to AC-4 (pin imprint=nist-800-53@rev5-dogfood-20261006)
edge: → conforms_to to SI-10 (pin imprint=nist-800-53@rev5-dogfood-20261006)
edge: → conforms_to to V-222425 (pin imprint=asd-stig@v6r4)
edge: → conforms_to to V-222606 (pin imprint=asd-stig@v6r4)
edge: → conforms_to to V-222444 (pin imprint=asd-stig@v6r4)
<<<
RELATIONS:
- TYPE: Parent
  VALUE: ARCH-ATTACH
- TYPE: Parent
  VALUE: ARCH-ATTACH
  ROLE: Refines
- TYPE: Parent
  VALUE: ARCH-SEC-REL-STUB
  ROLE: Uses
- TYPE: Parent
  VALUE: ARCH-SEC-XPROJ-READ
  ROLE: Uses
- TYPE: Parent
  VALUE: CAP-SVC-STRUCTURED-LOG
  ROLE: Uses
- TYPE: Parent
  VALUE: AC-3
  ROLE: ConformsTo
- TYPE: Parent
  VALUE: AC-4
  ROLE: ConformsTo
- TYPE: Parent
  VALUE: SI-10
  ROLE: ConformsTo
- TYPE: Parent
  VALUE: V-222425
  ROLE: ConformsTo
- TYPE: Parent
  VALUE: V-222606
  ROLE: ConformsTo
- TYPE: Parent
  VALUE: V-222444
  ROLE: ConformsTo
- TYPE: Parent
  VALUE: ARCH-API-RBAC.1
  ROLE: Uses
- TYPE: Child
  VALUE: CONTRACT-ctr-reqalm-product
  ROLE: InScopeOf

[REQUIREMENT]
UID: ARCH-ATTACH-SCOPE.1
STATUS: Draft
TITLE: Attachment read inherits parent scope, redaction, and id validation
STATEMENT: >>>
Access to an attachment follows its parent object's scope and role permissions at every parent level: listing or downloading requires the read permission of the parent as granted by the caller's role (client read for a client-level attachment, project read for a project, requirement:read for a requirement version, and so on), checked server-side on every request; creating or deleting requires the parent's write-level permission plus attachment:create. There is no attachment-specific grant model. If the caller cannot read the parent, or the parent or attachment is restricted for the caller, or the attachment is soft-deleted, the response is the same 404 as a nonexistent id, with no difference in body, headers, or timing class. Attachment ids, attachment version ids, and blob ids are server-generated and must match their allowlists (^att_[0-9a-z]{26}$, ^attv_[0-9a-z]{26}$, ^blob_[0-9a-f]{64}$); blob ids are internal and never accepted from clients; any other value is rejected with 400 before any lookup, and the raw value is not logged (logs record a redacted placeholder). List responses return metadata only: attachment id, attachment version id and version number (latest labeled), sanitized display name, size in bytes, media type (as detected), sha256, scan state, uploaded_by identity_id, created_at. They never return storage keys, object-store URLs, or content.
<<<
COMMENT: >>>
KIND: requirement
BASE_UID: ARCH-ATTACH-SCOPE
VERSION_N: 1
rbac_op: attachment:read
priority: 5
iteration: iter-r1
security.catalog_ref: AC-3
security.verification_note: Cyber 2026-10-09 attachments delta v3; content mint: id allowlists for attachment version and blob ids; list shows version.
edge: ← satisfies from CAP-ATTACH-READ
edge: → conforms_to to AC-3 (pin imprint=nist-800-53@rev5-dogfood-20261006)
edge: → conforms_to to AC-4 (pin imprint=nist-800-53@rev5-dogfood-20261006)
edge: → conforms_to to SI-10 (pin imprint=nist-800-53@rev5-dogfood-20261006)
edge: → conforms_to to V-222425 (pin imprint=asd-stig@v6r4)
edge: → conforms_to to V-222606 (pin imprint=asd-stig@v6r4)
edge: → conforms_to to V-222444 (pin imprint=asd-stig@v6r4)
<<<
RELATIONS:
- TYPE: Parent
  VALUE: ARCH-ATTACH
- TYPE: Parent
  VALUE: ARCH-ATTACH
  ROLE: Refines
- TYPE: Parent
  VALUE: ARCH-SEC-REL-STUB
  ROLE: Uses
- TYPE: Parent
  VALUE: ARCH-SEC-XPROJ-READ
  ROLE: Uses
- TYPE: Parent
  VALUE: ARCH-API-RBAC.1
  ROLE: Uses
- TYPE: Parent
  VALUE: CAP-SVC-STRUCTURED-LOG
  ROLE: Uses
- TYPE: Parent
  VALUE: AC-3
  ROLE: ConformsTo
- TYPE: Parent
  VALUE: AC-4
  ROLE: ConformsTo
- TYPE: Parent
  VALUE: SI-10
  ROLE: ConformsTo
- TYPE: Parent
  VALUE: V-222425
  ROLE: ConformsTo
- TYPE: Parent
  VALUE: V-222606
  ROLE: ConformsTo
- TYPE: Parent
  VALUE: V-222444
  ROLE: ConformsTo

[REQUIREMENT]
UID: ARCH-ATTACH-AUDIT
STATUS: Draft
TITLE: Every attachment access and change is audited
STATEMENT: >>>
Every attachment download, upload, carry-forward, soft delete, and wipe, whether allowed or denied, writes one append-only audit_events row with: actor identity_id, client_id, project_id, action, attachment id, parent ref (kind and uid), content sha256, outcome, and trace_id. Audit rows never contain file content, file names supplied by the user before sanitization, or storage keys. List calls are audited as one row per request, not per item. Audit writes go through the write unit of work; if the audit row cannot be written, the download is refused.
<<<
COMMENT: >>>
KIND: requirement
BASE_UID: ARCH-ATTACH-AUDIT
VERSION_N: 0
rbac_op: attachment:read
priority: 5
iteration: iter-r1
security.catalog_ref: AU-2
security.verification_note: Cyber 2026-10-09 attachments-figma mapping; Object-access audit per STIG V-222465.
edge: ← uses from ARCH-ATTACH-SCAN
edge: ← uses from ARCH-FIGMA-EGRESS
edge: ← satisfies from CAP-ATTACH-READ
edge: ← uses from ARCH-ATTACH-VERSIONS
in_scope_of_contract: ReqALM product (build)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
edge: → conforms_to to V-222465 (pin imprint=asd-stig@v6r4)
edge: → conforms_to to V-222444 (pin imprint=asd-stig@v6r4)
<<<
RELATIONS:
- TYPE: Parent
  VALUE: ARCH-ATTACH
- TYPE: Parent
  VALUE: ARCH-ATTACH
  ROLE: Refines
- TYPE: Parent
  VALUE: ARCH-WRITE-UOW-AUDIT
  ROLE: Uses
- TYPE: Parent
  VALUE: CAP-SVC-AUDIT-APPEND
  ROLE: Uses
- TYPE: Parent
  VALUE: ARCH-WRITE-AUDIT-FLOOD
  ROLE: Uses
- TYPE: Parent
  VALUE: AU-2
  ROLE: ConformsTo
- TYPE: Parent
  VALUE: AU-3
  ROLE: ConformsTo
- TYPE: Parent
  VALUE: AU-12
  ROLE: ConformsTo
- TYPE: Parent
  VALUE: V-222465
  ROLE: ConformsTo
- TYPE: Parent
  VALUE: V-222444
  ROLE: ConformsTo
- TYPE: Child
  VALUE: CONTRACT-ctr-reqalm-product
  ROLE: InScopeOf

[REQUIREMENT]
UID: ARCH-ATTACH-SERVE
STATUS: Draft
TITLE: Attachments are served as downloads, never rendered inline
STATEMENT: >>>
Attachment bytes are served only from a dedicated download route with Content-Disposition: attachment and an RFC 6266 filename (ASCII fallback plus filename* UTF-8 percent-encoding, with path separators, control characters, and quotes removed), Content-Type set from the detected type (application/octet-stream when unknown or not on the allowlist), X-Content-Type-Options: nosniff, Content-Security-Policy: sandbox; default-src 'none', Cache-Control: private, no-store, and Cross-Origin-Resource-Policy: same-origin. The UI never renders attachment content inline (no img, iframe, object, or embed of the raw bytes). SVG, HTML, XML, and other active-content types are always served as application/octet-stream downloads. Before returning bytes, the server recomputes sha256 and compares it with the stored value; a mismatch returns an error, is audited, and marks the attachment integrity_failed.
<<<
COMMENT: >>>
KIND: requirement
BASE_UID: ARCH-ATTACH-SERVE
VERSION_N: 0
rbac_op: attachment:read
priority: 5
iteration: iter-r1
security.catalog_ref: SI-10
security.verification_note: Cyber 2026-10-09 attachments-figma mapping; Stored-XSS containment; extends ARCH-SEC-HEADERS.
edge: ← uses from ARCH-FIGMA
edge: ← satisfies from CAP-ATTACH-READ
in_scope_of_contract: ReqALM product (build)
edge: → conforms_to to SI-10 (pin imprint=nist-800-53@rev5-dogfood-20261006)
edge: → conforms_to to SI-7 (pin imprint=nist-800-53@rev5-dogfood-20261006)
edge: → conforms_to to SC-18 (pin imprint=nist-800-53@rev5-dogfood-20261006)
edge: → conforms_to to V-222602 (pin imprint=asd-stig@v6r4)
edge: → conforms_to to V-222609 (pin imprint=asd-stig@v6r4)
<<<
RELATIONS:
- TYPE: Parent
  VALUE: ARCH-ATTACH
- TYPE: Parent
  VALUE: ARCH-ATTACH
  ROLE: Refines
- TYPE: Parent
  VALUE: ARCH-SEC-HEADERS
  ROLE: Refines
- TYPE: Parent
  VALUE: SI-10
  ROLE: ConformsTo
- TYPE: Parent
  VALUE: SI-7
  ROLE: ConformsTo
- TYPE: Parent
  VALUE: SC-18
  ROLE: ConformsTo
- TYPE: Parent
  VALUE: V-222602
  ROLE: ConformsTo
- TYPE: Parent
  VALUE: V-222609
  ROLE: ConformsTo
- TYPE: Child
  VALUE: CONTRACT-ctr-reqalm-product
  ROLE: InScopeOf

[REQUIREMENT]
UID: ARCH-ATTACH-UPLOAD
STATUS: Draft
TITLE: Upload: write permission, validation, size and quota
STATEMENT: >>>
Uploading requires attachment:create on the parent's project, which is separate from read and is granted to Author and above. Upload is a same-origin POST protected by the session CSRF defenses (ARCH-SEC-HEADERS, SameSite cookies, Origin check). The server rejects any file larger than 25 MB (26,214,400 bytes) and any upload that would take the project's total attachment storage above 5 GB (5,368,709,120 bytes), counting soft-deleted attachments until wiped, before accepting the bytes. The type is decided from magic bytes against an allowlist (initially PDF, PNG, JPEG, plain text, CSV, and Office Open XML), never from the extension or client Content-Type; a mismatch is rejected with 400. Accepted files enter quarantine and become available only per ARCH-ATTACH-SCAN.
<<<
COMMENT: >>>
KIND: requirement
BASE_UID: ARCH-ATTACH-UPLOAD
VERSION_N: 0
rbac_op: attachment:create
priority: 20
iteration: iter-r1
security.catalog_ref: SI-10
security.verification_note: Cyber 2026-10-09 attachments-figma mapping; Write phase (later). Scanning is in ARCH-ATTACH-SCAN.
edge: ← satisfies from CAP-ATTACH-WRITE
in_scope_of_contract: ReqALM product (build)
edge: → conforms_to to SI-10 (pin imprint=nist-800-53@rev5-dogfood-20261006)
edge: → conforms_to to CM-7 (pin imprint=nist-800-53@rev5-dogfood-20261006)
edge: → conforms_to to AC-3 (pin imprint=nist-800-53@rev5-dogfood-20261006)
edge: → conforms_to to V-222606 (pin imprint=asd-stig@v6r4)
edge: → conforms_to to V-222603 (pin imprint=asd-stig@v6r4)
edge: → conforms_to to V-222429 (pin imprint=asd-stig@v6r4)
<<<
RELATIONS:
- TYPE: Parent
  VALUE: ARCH-ATTACH
- TYPE: Parent
  VALUE: ARCH-ATTACH
  ROLE: Refines
- TYPE: Parent
  VALUE: ARCH-ATTACH-SCAN
  ROLE: Uses
- TYPE: Parent
  VALUE: SI-10
  ROLE: ConformsTo
- TYPE: Parent
  VALUE: CM-7
  ROLE: ConformsTo
- TYPE: Parent
  VALUE: AC-3
  ROLE: ConformsTo
- TYPE: Parent
  VALUE: V-222606
  ROLE: ConformsTo
- TYPE: Parent
  VALUE: V-222603
  ROLE: ConformsTo
- TYPE: Parent
  VALUE: V-222429
  ROLE: ConformsTo
- TYPE: Parent
  VALUE: ARCH-API-RBAC.1
  ROLE: Uses
- TYPE: Child
  VALUE: CONTRACT-ctr-reqalm-product
  ROLE: InScopeOf

[REQUIREMENT]
UID: ARCH-ATTACH-ENCRYPT
STATUS: Draft
TITLE: Attachment encryption at rest via KeyProvider envelope
STATEMENT: >>>
Each attachment object is encrypted at rest with its own data encryption key (AES-256-GCM); the DEK is wrapped by the KeyProvider KEK (ARCH-KEY-PROVIDER) and stored beside the metadata row, scoped to the client. Plaintext DEKs exist only in memory for one request. If the KeyProvider is unavailable, uploads and downloads fail closed (ARCH-KEY-FAILCLOSED). Wipe destroys the wrapped DEK as well as the object (crypto-shred). Object-store credentials are held in the key store and never logged.
<<<
COMMENT: >>>
KIND: requirement
BASE_UID: ARCH-ATTACH-ENCRYPT
VERSION_N: 0
rbac_op: attachment:create
priority: 20
iteration: iter-r1
security.catalog_ref: SC-28
security.verification_note: Cyber 2026-10-09 attachments-figma mapping; Extends ARCH-KEY-SCOPE item list with attachment DEKs.
edge: ← satisfies from CAP-ATTACH-WRITE
in_scope_of_contract: ReqALM product (build)
edge: → conforms_to to SC-28 (pin imprint=nist-800-53@rev5-dogfood-20261006)
edge: → conforms_to to SC-12 (pin imprint=nist-800-53@rev5-dogfood-20261006)
edge: → conforms_to to V-222588 (pin imprint=asd-stig@v6r4)
edge: → conforms_to to V-222587 (pin imprint=asd-stig@v6r4)
<<<
RELATIONS:
- TYPE: Parent
  VALUE: ARCH-ATTACH
- TYPE: Parent
  VALUE: ARCH-ATTACH
  ROLE: Refines
- TYPE: Parent
  VALUE: ARCH-KEY-PROVIDER
  ROLE: Uses
- TYPE: Parent
  VALUE: ARCH-KEY-SCOPE.1
  ROLE: Refines
- TYPE: Parent
  VALUE: ARCH-KEY-FAILCLOSED
  ROLE: Uses
- TYPE: Parent
  VALUE: SC-28
  ROLE: ConformsTo
- TYPE: Parent
  VALUE: SC-12
  ROLE: ConformsTo
- TYPE: Parent
  VALUE: V-222588
  ROLE: ConformsTo
- TYPE: Parent
  VALUE: V-222587
  ROLE: ConformsTo
- TYPE: Child
  VALUE: CONTRACT-ctr-reqalm-product
  ROLE: InScopeOf

[REQUIREMENT]
UID: ARCH-ATTACH-ENCRYPT.1
STATUS: Draft
TITLE: Attachment encryption at rest via KeyProvider envelope
STATEMENT: >>>
Each blob is encrypted at rest with its own data encryption key (AES-256-GCM); the DEK is wrapped by the KeyProvider KEK (ARCH-KEY-PROVIDER) and stored beside the blob metadata, scoped to the client. All attachment versions and pins that link the same blob share its DEK. Plaintext DEKs exist only in memory for one request. If the KeyProvider is unavailable, uploads and downloads fail closed (ARCH-KEY-FAILCLOSED). The wrapped DEK is destroyed together with the blob when its reference count reaches zero or when the blob is wiped (crypto-shred). Object-store credentials are held in the key store and never logged.
<<<
COMMENT: >>>
KIND: requirement
BASE_UID: ARCH-ATTACH-ENCRYPT
VERSION_N: 1
rbac_op: attachment:create
priority: 20
iteration: iter-r1
security.catalog_ref: SC-28
security.verification_note: Cyber 2026-10-09 attachments delta v3; content mint: per-blob DEK shared by links; destroyed at refcount zero or wipe.
edge: ← satisfies from CAP-ATTACH-WRITE
edge: → conforms_to to SC-28 (pin imprint=nist-800-53@rev5-dogfood-20261006)
edge: → conforms_to to SC-12 (pin imprint=nist-800-53@rev5-dogfood-20261006)
edge: → conforms_to to V-222588 (pin imprint=asd-stig@v6r4)
edge: → conforms_to to V-222587 (pin imprint=asd-stig@v6r4)
<<<
RELATIONS:
- TYPE: Parent
  VALUE: ARCH-ATTACH
- TYPE: Parent
  VALUE: ARCH-ATTACH
  ROLE: Refines
- TYPE: Parent
  VALUE: ARCH-KEY-PROVIDER
  ROLE: Uses
- TYPE: Parent
  VALUE: ARCH-KEY-SCOPE.1
  ROLE: Refines
- TYPE: Parent
  VALUE: ARCH-KEY-FAILCLOSED
  ROLE: Uses
- TYPE: Parent
  VALUE: SC-28
  ROLE: ConformsTo
- TYPE: Parent
  VALUE: SC-12
  ROLE: ConformsTo
- TYPE: Parent
  VALUE: V-222588
  ROLE: ConformsTo
- TYPE: Parent
  VALUE: V-222587
  ROLE: ConformsTo
- TYPE: Parent
  VALUE: ARCH-ATTACH-VERSIONS
  ROLE: Uses

[REQUIREMENT]
UID: ARCH-ATTACH-SCAN
STATUS: Draft
TITLE: Pluggable malware scanner; quarantine until clean
STATEMENT: >>>
Every uploaded attachment is scanned through a pluggable scanner interface scan(stream) -> clean | infected | error, and each result records the engine name, engine version, and signature version. A new attachment stays in scan_state pending (quarantined) and cannot be listed as available or downloaded until a scan returns clean. An error or timeout leaves it quarantined (fail closed) and it may be retried. An infected attachment moves to scan_state infected, is never served, stays quarantined, and is retained per the soft-delete rule (ARCH-ATTACH) until wiped. Every scan result is written as an audit_events row (attachment id, parent ref, sha256, result, engine and signature version) and an infected result raises an alert. Rescanning clean attachments after a signature update is optional per deployment. The ClamAV (clamd) adapter is allowed in development only; production scanner selection is deferred, and production startup refuses to start with the dev adapter unless an operator explicitly configures it.
<<<
COMMENT: >>>
KIND: requirement
BASE_UID: ARCH-ATTACH-SCAN
VERSION_N: 0
rbac_op: attachment:create
priority: 20
iteration: iter-r1
security.catalog_ref: SI-3
security.verification_note: Cyber 2026-10-09 attachments-figma mapping; No ASD V6R4 seed item covers malicious-code scanning; SI-3/SI-8 stand without a STIG pair.
edge: ← uses from ARCH-ATTACH-UPLOAD
edge: ← satisfies from CAP-ATTACH-WRITE
in_scope_of_contract: ReqALM product (build)
edge: → conforms_to to SI-3 (pin imprint=nist-800-53@rev5-dogfood-20261006)
edge: → conforms_to to SI-8 (pin imprint=nist-800-53@rev5-dogfood-20261006)
edge: → conforms_to to CM-7 (pin imprint=nist-800-53@rev5-dogfood-20261006)
<<<
RELATIONS:
- TYPE: Parent
  VALUE: ARCH-ATTACH
- TYPE: Parent
  VALUE: ARCH-ATTACH
  ROLE: Refines
- TYPE: Parent
  VALUE: ARCH-ATTACH-AUDIT
  ROLE: Uses
- TYPE: Parent
  VALUE: SI-3
  ROLE: ConformsTo
- TYPE: Parent
  VALUE: SI-8
  ROLE: ConformsTo
- TYPE: Parent
  VALUE: CM-7
  ROLE: ConformsTo
- TYPE: Child
  VALUE: CONTRACT-ctr-reqalm-product
  ROLE: InScopeOf

[REQUIREMENT]
UID: ARCH-ATTACH-VERSIONS
STATUS: Draft
TITLE: Attachments are versioned lines over content-addressed blobs
STATEMENT: >>>
An attachment is a line with a stable attachment id (^att_[0-9a-z]{26}$) and immutable versions numbered 1, 2, and so on. Each attachment version has its own id (^attv_[0-9a-z]{26}$) and references exactly one stored blob, identified by its sha256 and blob id (^blob_[0-9a-f]{64}$, the hex sha256). Blobs are content-addressed and written once; an attachment version's blob, sha256, size, media type, and scan result never change. Adding a file version creates a new attachment version and never changes existing pins. Carry-forward is an explicit request that creates a new pin from a target parent to an existing attachment version and links the same blob; bytes are never copied. It requires attachment:create on the target parent and read on the source, the source and target must be in the same project (no cross-project carry-forward), and every link and unlink is audited. Blobs are reference-counted over live pins. Soft-deleting a pin decrements nothing until wipe; a blob and its wrapped DEK are destroyed when no live or soft-deleted pin references it. attachment:wipe on a blob is an explicit Client admin action with step-up that tombstones every pin referencing the blob in that project, destroys the blob and its DEK, and writes one audit row listing every affected pin.
<<<
COMMENT: >>>
KIND: requirement
BASE_UID: ARCH-ATTACH-VERSIONS
VERSION_N: 0
rbac_op: attachment:read
priority: 10
iteration: iter-r1
security.catalog_ref: CM-3
security.verification_note: Cyber 2026-10-09 attachments delta v3; versioned attachment lines, content-addressed blobs, same-project carry-forward by link, refcounted wipe.
edge: ← uses from ARCH-ATTACH-PIN-VERSION.1
edge: ← uses from ARCH-ATTACH-ENCRYPT.1
edge: ← satisfies from CAP-ATTACH-READ
edge: ← satisfies from CAP-ATTACH-WRITE
in_scope_of_contract: ReqALM product (build)
edge: → conforms_to to CM-3 (pin imprint=nist-800-53@rev5-dogfood-20261006)
edge: → conforms_to to CM-2 (pin imprint=nist-800-53@rev5-dogfood-20261006)
edge: → conforms_to to AU-9 (pin imprint=nist-800-53@rev5-dogfood-20261006)
edge: → conforms_to to SI-7 (pin imprint=nist-800-53@rev5-dogfood-20261006)
edge: → conforms_to to AU-10 (pin imprint=nist-800-53@rev5-dogfood-20261006)
edge: → conforms_to to V-222588 (pin imprint=asd-stig@v6r4)
<<<
RELATIONS:
- TYPE: Parent
  VALUE: ARCH-ATTACH
- TYPE: Parent
  VALUE: ARCH-ATTACH
  ROLE: Refines
- TYPE: Parent
  VALUE: ARCH-ATTACH-AUDIT
  ROLE: Uses
- TYPE: Parent
  VALUE: ARCH-MINT-KIND
  ROLE: Refines
- TYPE: Parent
  VALUE: CM-3
  ROLE: ConformsTo
- TYPE: Parent
  VALUE: CM-2
  ROLE: ConformsTo
- TYPE: Parent
  VALUE: AU-9
  ROLE: ConformsTo
- TYPE: Parent
  VALUE: SI-7
  ROLE: ConformsTo
- TYPE: Parent
  VALUE: AU-10
  ROLE: ConformsTo
- TYPE: Parent
  VALUE: V-222588
  ROLE: ConformsTo
- TYPE: Child
  VALUE: CONTRACT-ctr-reqalm-product
  ROLE: InScopeOf

[[/SECTION]]

[REQUIREMENT]
UID: CAP-ATTACH-READ
STATUS: Draft
TITLE: Attachment metadata list + download (read-only)
STATEMENT: >>>
Attachment tables (migration with scope, soft delete, scan_state, sha256, wrapped DEK columns), metadata list and download routes under the requirement-read guard, id allowlist with 400 beds, same-404 restricted beds, append-only download audit, and download headers per ARCH-ATTACH-SERVE. Seed attachments are loaded by the dogfood loader only.
<<<
COMMENT: >>>
KIND: capability
BASE_UID: CAP-ATTACH-READ
VERSION_N: 0
rbac_op: attachment:read
priority: 10
iteration: iter-r1
security.catalog_ref: AC-3
security.verification_note: Cyber 2026-10-09 attachments-figma mapping; Planned; phase 1.
edge: ← uses from CAP-ATTACH-WRITE
edge: ← refines from CAP-READ-ARTIFACTS
in_scope_of_contract: ReqALM product (build)
edge: → conforms_to to AC-3 (pin imprint=nist-800-53@rev5-dogfood-20261006)
edge: → conforms_to to AU-12 (pin imprint=nist-800-53@rev5-dogfood-20261006)
edge: → conforms_to to SI-10 (pin imprint=nist-800-53@rev5-dogfood-20261006)
<<<
RELATIONS:
- TYPE: Parent
  VALUE: SEC-SEC
- TYPE: Parent
  VALUE: ARCH-ATTACH
  ROLE: Satisfies
- TYPE: Parent
  VALUE: ARCH-ATTACH-SCOPE
  ROLE: Satisfies
- TYPE: Parent
  VALUE: ARCH-ATTACH-AUDIT
  ROLE: Satisfies
- TYPE: Parent
  VALUE: ARCH-ATTACH-SERVE
  ROLE: Satisfies
- TYPE: Parent
  VALUE: ARCH-ATTACH-PIN-VERSION
  ROLE: Satisfies
- TYPE: Parent
  VALUE: AC-3
  ROLE: ConformsTo
- TYPE: Parent
  VALUE: AU-12
  ROLE: ConformsTo
- TYPE: Parent
  VALUE: SI-10
  ROLE: ConformsTo
- TYPE: Parent
  VALUE: ARCH-ATTACH-VERSIONS
  ROLE: Satisfies
- TYPE: Parent
  VALUE: ARCH-ATTACH-PIN-VERSION.1
  ROLE: Satisfies
- TYPE: Parent
  VALUE: ARCH-ATTACH-SCOPE.1
  ROLE: Satisfies
- TYPE: Child
  VALUE: CONTRACT-ctr-reqalm-product
  ROLE: InScopeOf

[REQUIREMENT]
UID: CAP-ATTACH-WRITE
STATUS: Draft
TITLE: Attachment upload, scan, encryption, soft delete
STATEMENT: >>>
Upload route with attachment:create, CSRF and Origin checks, size cap and project quota, magic-byte type allowlist, pending/clean/quarantined scan pipeline, KeyProvider envelope encryption per object, explicit carry-forward to a new version, soft delete, and Client admin wipe with step-up.
<<<
COMMENT: >>>
KIND: capability
BASE_UID: CAP-ATTACH-WRITE
VERSION_N: 0
rbac_op: attachment:create
priority: 20
iteration: iter-r1
security.catalog_ref: SI-3
security.verification_note: Cyber 2026-10-09 attachments-figma mapping; Planned; phase 2.
in_scope_of_contract: ReqALM product (build)
edge: → conforms_to to SI-3 (pin imprint=nist-800-53@rev5-dogfood-20261006)
edge: → conforms_to to SC-28 (pin imprint=nist-800-53@rev5-dogfood-20261006)
<<<
RELATIONS:
- TYPE: Parent
  VALUE: SEC-SEC
- TYPE: Parent
  VALUE: ARCH-ATTACH-UPLOAD
  ROLE: Satisfies
- TYPE: Parent
  VALUE: ARCH-ATTACH-SCAN
  ROLE: Satisfies
- TYPE: Parent
  VALUE: ARCH-ATTACH-ENCRYPT
  ROLE: Satisfies
- TYPE: Parent
  VALUE: ARCH-ATTACH-PIN-VERSION
  ROLE: Satisfies
- TYPE: Parent
  VALUE: SI-3
  ROLE: ConformsTo
- TYPE: Parent
  VALUE: SC-28
  ROLE: ConformsTo
- TYPE: Parent
  VALUE: CAP-ATTACH-READ
  ROLE: Uses
- TYPE: Parent
  VALUE: ARCH-ATTACH-VERSIONS
  ROLE: Satisfies
- TYPE: Parent
  VALUE: ARCH-ATTACH-PIN-VERSION.1
  ROLE: Satisfies
- TYPE: Parent
  VALUE: ARCH-ATTACH-ENCRYPT.1
  ROLE: Satisfies
- TYPE: Child
  VALUE: CONTRACT-ctr-reqalm-product
  ROLE: InScopeOf

[REQUIREMENT]
UID: CAP-SVC-RBAC-NO-PROJECT
STATUS: Active
TITLE: RBAC authorize fails closed without project scope
STATEMENT: >>>
authorize() and listActiveRoles() fail closed when no project id is supplied: project_grants roles apply only when projectId matches; permissions other than platform Key custodian key:manage and audit:read are denied without a project scope, so a route that omits projectScoped cannot authorize via another project's grant.
<<<
COMMENT: >>>
KIND: capability
BASE_UID: CAP-SVC-RBAC-NO-PROJECT
VERSION_N: 0
priority: 10
iteration: iter-r1
security.catalog_ref: AC-3
security.verification_note: Shipped with RBAC authorize fail-closed PR #46 (merge d54c5a67235fd56e49bdbc2a939dce89ff5a4f36).
edge: ← refines from CAP-SVC-HARDENING-FOLLOWUP
delivered_by_release: R1 — RBAC authorize fail closed (no project scope)
<<<
RELATIONS:
- TYPE: Parent
  VALUE: SEC-SEC
- TYPE: Parent
  VALUE: ARCH-API-RBAC
  ROLE: Satisfies
- TYPE: Parent
  VALUE: CAP-RBAC
  ROLE: Satisfies
- TYPE: Parent
  VALUE: CAP-SVC-OPERATION-EXECUTOR
  ROLE: Satisfies
- TYPE: Child
  VALUE: RELEASE-rel-r1-rbac-authorize-fail-closed
  ROLE: Delivers

[[/SECTION]]

[[SECTION]]
UID: SEC-MCP
TITLE: MCP agent desks

[TEXT]
UID: SEC-MCP-INTRO
STATEMENT: >>>
MCP agents authenticate like UI users, bind to a requirements desk (browser tab routing), mutate via HTTPS API, and receive live desk pushes on a session-sealed WebSocket.
<<<

[REQUIREMENT]
UID: CAP-MCP-DESK
STATUS: Draft
TITLE: ReqALM MCP requirements desk channel
STATEMENT: >>>
Capability pack for ReqALM MCP server, desk list/attach, and session-sealed desk WebSocket.
Mutations stay on HTTPS; the desk socket is push-only. MCP authorization reuses the same RBAC pack as the
UI (MC03); race-safe session sealing maps to V-222567.
<<<
COMMENT: >>>
KIND: capability
BASE_UID: CAP-MCP-DESK
VERSION_N: 0
priority: 10
iteration: iter-r0
security.catalog_ref: AC-3
security.verification_note: AC-3 access enforcement; AU-2/3/12 where mutating.
edge: ← uses from ARCH-DEPLOY-MINIMAL
edge: ← refines from ARCH-AUTH-MCP-REQUIRED
in_scope_of_contract: Security package
in_scope_of_contract: ReqALM product (build)
edge: → conforms_to to AC-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
<<<
RELATIONS:
- TYPE: Parent
  VALUE: SEC-MCP
- TYPE: Parent
  VALUE: MC01.1
  ROLE: Satisfies
- TYPE: Parent
  VALUE: MC02
  ROLE: Satisfies
- TYPE: Parent
  VALUE: MC03
  ROLE: Satisfies
- TYPE: Parent
  VALUE: AC-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Child
  VALUE: CONTRACT-contract-security-package
  ROLE: InScopeOf
- TYPE: Child
  VALUE: CONTRACT-ctr-reqalm-product
  ROLE: InScopeOf

[REQUIREMENT]
UID: MC01
STATUS: Draft
TITLE: MCP authenticate session & desk bind
STATEMENT: >>>
An MCP host connects to ReqALM MCP (stdio or Streamable HTTP), establishes a platform session
(OAuth opaque token or login aligned with A01), lists desks, and attach/detach routing to a browser
requirements desk; live pushes use session-sealed WSS.
<<<
COMMENT: >>>
KIND: requirement
BASE_UID: MC01
VERSION_N: 0
rbac_op: mcp:session:create, desk:list, desk:attach, desk:detach
priority: 60
iteration: iter-r0
security.catalog_ref: SC-8
security.verification_note: NIST IA/AC/AU/SC; desk sealing pattern (OC ADR 0018 analogue). ASD STIG V6R4 V-222567 / V-222596.
edge: → conforms_to to V-222567 (pin imprint=asd-stig@v6r4)
edge: → conforms_to to V-222596 (pin imprint=asd-stig@v6r4)
edge: → conforms_to to SC-8 (pin imprint=nist-800-53@rev5-dogfood-20261006)
<<<
RELATIONS:
- TYPE: Parent
  VALUE: SEC-MCP
- TYPE: Parent
  VALUE: V-222567
  ROLE: ConformsTo
- TYPE: Parent
  VALUE: V-222596
  ROLE: ConformsTo
- TYPE: Parent
  VALUE: SC-8
  ROLE: ConformsTo

[REQUIREMENT]
UID: MC01.1
STATUS: Draft
TITLE: MCP authenticate session & desk bind
STATEMENT: >>>
An MCP host authenticates with the same enterprise identity path as UI users (A01-aligned), lists
requirements desks, and attaches to exactly one desk for live preview. Session tokens are opaque; desk
WebSocket traffic is sealed to the session. Mutating tools are not exposed on the desk socket.
<<<
COMMENT: >>>
KIND: requirement
BASE_UID: MC01
VERSION_N: 1
rbac_op: mcp:session:create, desk:list, desk:attach, desk:detach
priority: 55
iteration: iter-r1
security.catalog_ref: SC-8
security.verification_note: Draft successor refining desk-seal wording. ASD STIG V6R4 V-222567 / V-222396.
edge: ← satisfies from CAP-MCP-DESK
edge: ← refines from ARCH-AUTH-AS
edge: ← refines from ARCH-AUTH-METADATA
edge: ← refines from ARCH-AUTH-MCP-REQUIRED
in_scope_of_contract: Design-2026-10
in_scope_of_contract: Security package
in_scope_of_contract: ReqALM product (build)
delivered_by_release: R0-sequences
edge: → conforms_to to SC-8 (pin imprint=nist-800-53@rev5-dogfood-20261006)
edge: → conforms_to to SC-13 (pin imprint=nist-800-53@rev5-dogfood-20261006)
edge: → conforms_to to V-222567 (pin imprint=asd-stig@v6r4)
edge: → conforms_to to V-222396 (pin imprint=asd-stig@v6r4)
<<<
RELATIONS:
- TYPE: Parent
  VALUE: SEC-MCP
- TYPE: Parent
  VALUE: SC-8
  ROLE: ConformsTo
- TYPE: Parent
  VALUE: A01
  ROLE: Refines
- TYPE: Parent
  VALUE: SC-13
  ROLE: ConformsTo
- TYPE: Parent
  VALUE: V-222567
  ROLE: ConformsTo
- TYPE: Parent
  VALUE: V-222396
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r0-sequences
  ROLE: Delivers

[REQUIREMENT]
UID: MC02
STATUS: Draft
TITLE: MCP mutating tool with desk attached
STATEMENT: >>>
With a desk attached, an MCP tool updates a draft requirement version field over HTTPS
(HTTP→business→data→Postgres), audits the agent write, and pushes preview to the desk channel.
Mutations never travel on the desk WebSocket.
<<<
COMMENT: >>>
KIND: requirement
BASE_UID: MC02
VERSION_N: 0
rbac_op: requirement:version:update_draft
priority: 60
iteration: iter-r0
security.catalog_ref: AC-3
security.verification_note: AC-3/CM-3/AU; mutations not on desk socket. ASD STIG V6R4 V-222567.
edge: ← satisfies from CAP-MCP-DESK
edge: ← uses from FIX-ALLOW-MCP-OAUTH-PKCE
edge: ← uses from ARCH-AUTH-AGENT-ATTRIBUTION
edge: ← uses from FIX-ALLOW-AGENT-ATTRIBUTION
in_scope_of_contract: Design-2026-10
in_scope_of_contract: Security package
in_scope_of_contract: ReqALM product (build)
delivered_by_release: R0-sequences
edge: → conforms_to to V-222567 (pin imprint=asd-stig@v6r4)
edge: → conforms_to to AC-3 (pin imprint=nist-800-53@rev5-dogfood-20261006)
edge: → conforms_to to CM-3 (pin imprint=nist-800-53@rev5-dogfood-20261006)
<<<
RELATIONS:
- TYPE: Parent
  VALUE: SEC-MCP
- TYPE: Parent
  VALUE: ARCH-API
  ROLE: Uses
- TYPE: Parent
  VALUE: D03
  ROLE: Uses
- TYPE: Parent
  VALUE: V-222567
  ROLE: ConformsTo
- TYPE: Parent
  VALUE: AC-3
  ROLE: ConformsTo
- TYPE: Parent
  VALUE: CM-3
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r0-sequences
  ROLE: Delivers

[REQUIREMENT]
UID: MC03
STATUS: Draft
TITLE: MCP tool RBAC mirrors UI permissions
STATEMENT: >>>
MCP tools enforce the same project_grant checks as UI/API callers for the authenticated identity.
An agent cannot escalate privileges by using MCP; denied tools return structured errors and audit events.
<<<
COMMENT: >>>
KIND: requirement
BASE_UID: MC03
VERSION_N: 0
rbac_op: mcp:authorize
priority: 55
iteration: iter-r1
security.catalog_ref: REQALM-SEC-RBAC
security.verification_note: MCP uses same RBAC pack as UI.
edge: ← satisfies from CAP-MCP-DESK
edge: ← refines from FIX-DENY-MCP-ESCALATE
edge: ← refines from ARCH-AUTH-AUDIENCE
edge: ← satisfies from CAP-REQALM-CONTRACTS
in_scope_of_contract: Design-2026-10
in_scope_of_contract: Security package
in_scope_of_contract: ReqALM product (build)
delivered_by_release: R1-core-ALM
edge: → conforms_to to AC-2 (pin imprint=nist-800-53@rev5-dogfood-20261006)
edge: → conforms_to to AC-6 (pin imprint=nist-800-53@rev5-dogfood-20261006)
edge: → conforms_to to V-222429 (pin imprint=asd-stig@v6r4)
<<<
RELATIONS:
- TYPE: Parent
  VALUE: SEC-MCP
- TYPE: Parent
  VALUE: CAP-RBAC
  ROLE: Uses
- TYPE: Parent
  VALUE: AC-2
  ROLE: ConformsTo
- TYPE: Parent
  VALUE: AC-6
  ROLE: ConformsTo
- TYPE: Parent
  VALUE: V-222429
  ROLE: ConformsTo
- TYPE: Child
  VALUE: CONTRACT-contract-design-2026-10
  ROLE: InScopeOf
- TYPE: Child
  VALUE: CONTRACT-contract-security-package
  ROLE: InScopeOf
- TYPE: Child
  VALUE: CONTRACT-ctr-reqalm-product
  ROLE: InScopeOf
- TYPE: Child
  VALUE: RELEASE-rel-r1-core-alm
  ROLE: Delivers

[[/SECTION]]

[[SECTION]]
UID: SEC-FIX
TITLE: Security / QA fixtures (test beds)

[TEXT]
UID: SEC-FIX-INTRO
STATEMENT: >>>
Fixture and test-bed requirements for Cyber+QA denial, succession, contract-doc, and
release-snapshot scenarios. These are NOT product features — they document expected
deny/allow outcomes and seed data shapes for implementers and automated tests.
<<<

[REQUIREMENT]
UID: FIX-DENY-PRIORITY-UNAPPROVED
STATUS: Active
TITLE: Author denied priority set without stakeholder approval
STATEMENT: >>>
FIXTURE / TEST BED (not a product feature). Alex Author attempts requirement:version:priority on FIX-SAMPLE-UNAPPROVED whose line ApprovalRecord.status=unapproved (version mirror may also show unapproved) → expect HTTP 403/409 and an audit_events row (action=requirement:version:priority, outcome=deny). Gate gate-line-approved. Contrast FIX-SAMPLE-APPROVED / ar-fix-sample-approved.
<<<
COMMENT: >>>
KIND: requirement
BASE_UID: FIX-DENY-PRIORITY-UNAPPROVED
VERSION_N: 0
rbac_op: requirement:version:priority
priority: 20
iteration: iter-r1
security.catalog_ref: AC-3
security.verification_note: Priority requires stakeholder approval. Pairs FIX-SAMPLE-UNAPPROVED.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: FIX-SAMPLE-APPROVED
STATUS: Active
TITLE: Sample approved version (priority allowed)
STATEMENT: >>>
SAMPLE / FIXTURE: line FIX-SAMPLE-APPROVED has ApprovalRecord.status=approved (ar-fix-sample-approved) so D08 priority and grooming are allowed. Version.stakeholder_approval mirrors the line record. grooming_state=wi_ready; has work_item_link wil-fix-approved-ado.
<<<
COMMENT: >>>
KIND: requirement
BASE_UID: FIX-SAMPLE-APPROVED
VERSION_N: 0
priority: 10
iteration: iter-r1
security.catalog_ref: AC-3
security.verification_note: Approved sample for priority + WI path.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: FIX-SAMPLE-UNAPPROVED
STATUS: Active
TITLE: Sample unapproved version (priority denied)
STATEMENT: >>>
SAMPLE / FIXTURE: line FIX-SAMPLE-UNAPPROVED has ApprovalRecord.status=unapproved (ar-fix-sample-unapproved). Priority must be null; attempts to set priority deny (FIX-DENY-PRIORITY-UNAPPROVED). grooming_state=want. Version mirror shows unapproved.
<<<
COMMENT: >>>
KIND: requirement
BASE_UID: FIX-SAMPLE-UNAPPROVED
VERSION_N: 0
iteration: iter-r1
security.catalog_ref: AC-3
security.verification_note: Unapproved sample; priority blocked.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: FIX-DENY-READER-GRANT
STATUS: Active
TITLE: Casey Reader denied project:grant:create
STATEMENT: >>>
FIXTURE / TEST BED (not a product feature). Casey Reader (grant-casey-reader, role Reader)
attempts project:grant:create on reqaml → expect HTTP 403 and an audit_events row
(action=project:grant:create, outcome=deny, identity=casey-reader).
<<<
COMMENT: >>>
KIND: requirement
BASE_UID: FIX-DENY-READER-GRANT
VERSION_N: 0
rbac_op: project:grant:create
priority: 20
iteration: iter-r1
security.catalog_ref: REQALM-SEC-RBAC
security.verification_note: Reader cannot create grants; 403 + audit. Pairs grant-casey-reader.
in_scope_of_contract: ReqALM product (build)
edge: → conforms_to to AC-6 (pin imprint=nist-800-53@rev5-dogfood-20261006)
edge: → conforms_to to AU-6 (pin imprint=nist-800-53@rev5-dogfood-20261006)
edge: → conforms_to to CM-5 (pin imprint=nist-800-53@rev5-dogfood-20261006)
edge: → conforms_to to AC-2 (pin imprint=nist-800-53@rev5-dogfood-20261006)
edge: → conforms_to to V-222429 (pin imprint=asd-stig@v6r4)
<<<
RELATIONS:
- TYPE: Parent
  VALUE: SEC-FIX
- TYPE: Parent
  VALUE: AC-6
  ROLE: ConformsTo
- TYPE: Parent
  VALUE: AU-6
  ROLE: ConformsTo
- TYPE: Parent
  VALUE: CAP-RBAC
  ROLE: Uses
- TYPE: Parent
  VALUE: CM-5
  ROLE: ConformsTo
- TYPE: Parent
  VALUE: AC-2
  ROLE: ConformsTo
- TYPE: Parent
  VALUE: V-222429
  ROLE: ConformsTo
- TYPE: Child
  VALUE: CONTRACT-ctr-reqalm-product
  ROLE: InScopeOf

[REQUIREMENT]
UID: FIX-DENY-CROSS-CLIENT
STATUS: Active
TITLE: Dan scoped other-family cannot read reqalm tree
STATEMENT: >>>
FIXTURE / TEST BED (not a product feature). Dan with Client Scoped View set to
other-family must not read the reqaml project tree or versions under raby-family.
Expect 403 / empty scoped result and audit for cross-client read deny.
<<<
COMMENT: >>>
KIND: requirement
BASE_UID: FIX-DENY-CROSS-CLIENT
VERSION_N: 0
rbac_op: client:scope:select
priority: 20
iteration: iter-r1
security.catalog_ref: REQALM-SEC-SCOPE
security.verification_note: Server-side client scope blocks cross-client leakage into reqalm.
in_scope_of_contract: ReqALM product (build)
edge: → conforms_to to AC-6 (pin imprint=nist-800-53@rev5-dogfood-20261006)
edge: → conforms_to to AC-3 (pin imprint=nist-800-53@rev5-dogfood-20261006)
<<<
RELATIONS:
- TYPE: Parent
  VALUE: SEC-FIX
- TYPE: Parent
  VALUE: AC-6
  ROLE: ConformsTo
- TYPE: Parent
  VALUE: CAP-SCOPED-VIEW
  ROLE: Uses
- TYPE: Parent
  VALUE: AC-3
  ROLE: ConformsTo
- TYPE: Child
  VALUE: CONTRACT-ctr-reqalm-product
  ROLE: InScopeOf

[REQUIREMENT]
UID: FIX-DENY-STEWARD-STANDARD
STATUS: Active
TITLE: Non-steward denied catalog:entry:update on standard catalog
STATEMENT: >>>
FIXTURE / TEST BED (not a product feature). A non-steward identity attempting
catalog:entry:update on cat-nist-global (is_standard true) → expect HTTP 403.
Morgan steward grant covers only cat-reqaml-security, not the NIST standard catalog.
<<<
COMMENT: >>>
KIND: requirement
BASE_UID: FIX-DENY-STEWARD-STANDARD
VERSION_N: 0
rbac_op: catalog:entry:update
priority: 20
iteration: iter-r1
security.catalog_ref: REQALM-SEC-CATALOG
security.verification_note: Standard catalog edits steward-gated; NIST global is read-only for non-stewards.
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: SEC-FIX
- TYPE: Parent
  VALUE: AC-3
  ROLE: ConformsTo
- TYPE: Parent
  VALUE: CM-5
  ROLE: ConformsTo
- TYPE: Child
  VALUE: CONTRACT-ctr-reqalm-product
  ROLE: InScopeOf

[REQUIREMENT]
UID: FIX-DENY-MCP-ESCALATE
STATUS: Active
TITLE: MCP as Casey denied release:ship
STATEMENT: >>>
FIXTURE / TEST BED (not a product feature). MCP tools authenticated as Casey Reader
attempt release:ship → denied (same RBAC as UI). Pairs MC03 same-grant enforcement.
<<<
COMMENT: >>>
KIND: requirement
BASE_UID: FIX-DENY-MCP-ESCALATE
VERSION_N: 0
rbac_op: release:ship
priority: 20
iteration: iter-r1
security.catalog_ref: REQALM-SEC-RBAC
security.verification_note: MCP cannot escalate; Casey Reader lacks release:ship. Pairs MC03.
in_scope_of_contract: ReqALM product (build)
edge: → conforms_to to AC-2 (pin imprint=nist-800-53@rev5-dogfood-20261006)
edge: → conforms_to to AC-6 (pin imprint=nist-800-53@rev5-dogfood-20261006)
edge: → conforms_to to V-222429 (pin imprint=asd-stig@v6r4)
<<<
RELATIONS:
- TYPE: Parent
  VALUE: SEC-FIX
- TYPE: Parent
  VALUE: MC03
  ROLE: Refines
- TYPE: Parent
  VALUE: CAP-RBAC
  ROLE: Uses
- TYPE: Parent
  VALUE: AC-2
  ROLE: ConformsTo
- TYPE: Parent
  VALUE: AC-6
  ROLE: ConformsTo
- TYPE: Parent
  VALUE: V-222429
  ROLE: ConformsTo
- TYPE: Child
  VALUE: CONTRACT-ctr-reqalm-product
  ROLE: InScopeOf

[REQUIREMENT]
UID: FIX-DENY-NO-GRANT
STATUS: Active
TITLE: no-grant-user denied any project read
STATEMENT: >>>
FIXTURE / TEST BED (not a product feature). Identity no-grant-user (linked IdP,
zero project_grants) attempts any project read on reqaml → expect HTTP 403.
<<<
COMMENT: >>>
KIND: requirement
BASE_UID: FIX-DENY-NO-GRANT
VERSION_N: 0
rbac_op: project:read
priority: 20
iteration: iter-r1
security.catalog_ref: REQALM-SEC-RBAC
security.verification_note: No grant → deny all project reads. Identity present, grants empty.
in_scope_of_contract: ReqALM product (build)
edge: → conforms_to to AC-6 (pin imprint=nist-800-53@rev5-dogfood-20261006)
edge: → conforms_to to AC-2 (pin imprint=nist-800-53@rev5-dogfood-20261006)
edge: → conforms_to to V-222429 (pin imprint=asd-stig@v6r4)
<<<
RELATIONS:
- TYPE: Parent
  VALUE: SEC-FIX
- TYPE: Parent
  VALUE: AC-6
  ROLE: ConformsTo
- TYPE: Parent
  VALUE: CAP-RBAC
  ROLE: Uses
- TYPE: Parent
  VALUE: AC-2
  ROLE: ConformsTo
- TYPE: Parent
  VALUE: V-222429
  ROLE: ConformsTo
- TYPE: Child
  VALUE: CONTRACT-ctr-reqalm-product
  ROLE: InScopeOf

[REQUIREMENT]
UID: FIX-DENY-REVOKED
STATUS: Active
TITLE: Revoked grant write denied
STATEMENT: >>>
FIXTURE / TEST BED (not a product feature). Operating under tombstone
grant-alex-author-revoked (status=revoked) for a write → expect HTTP 403 + audit.
Live grant-alex-author remains for happy-path Author tests.
<<<
COMMENT: >>>
KIND: requirement
BASE_UID: FIX-DENY-REVOKED
VERSION_N: 0
rbac_op: requirement:version:create
priority: 20
iteration: iter-r1
security.catalog_ref: REQALM-SEC-RBAC
security.verification_note: Revoked grant tombstone cannot authorize writes. See grant-alex-author-revoked.
in_scope_of_contract: ReqALM product (build)
edge: → conforms_to to AC-3 (pin imprint=nist-800-53@rev5-dogfood-20261006)
edge: → conforms_to to AC-2 (pin imprint=nist-800-53@rev5-dogfood-20261006)
edge: → conforms_to to AC-6 (pin imprint=nist-800-53@rev5-dogfood-20261006)
edge: → conforms_to to V-222429 (pin imprint=asd-stig@v6r4)
<<<
RELATIONS:
- TYPE: Parent
  VALUE: SEC-FIX
- TYPE: Parent
  VALUE: CAP-RBAC
  ROLE: Uses
- TYPE: Parent
  VALUE: AC-3
  ROLE: ConformsTo
- TYPE: Parent
  VALUE: AC-2
  ROLE: ConformsTo
- TYPE: Parent
  VALUE: AC-6
  ROLE: ConformsTo
- TYPE: Parent
  VALUE: V-222429
  ROLE: ConformsTo
- TYPE: Child
  VALUE: CONTRACT-ctr-reqalm-product
  ROLE: InScopeOf

[REQUIREMENT]
UID: FIX-SUCC-2HOP
STATUS: Draft
TITLE: Two-hop succession with stale edge
STATEMENT: >>>
FIXTURE / TEST BED (not a product feature). Version .0 wording — superseded in-place when .1 then .2 became tip (≤1-active / D04). Detect bed for ARCH-SUSPECT.
<<<
COMMENT: >>>
KIND: requirement
BASE_UID: FIX-SUCC-2HOP
VERSION_N: 0
priority: 30
iteration: iter-r0
security.catalog_ref: CM-3
security.verification_note: Succession immutability / change control (CM-3).
edge: → conforms_to to CM-3 (pin imprint=nist-800-53@rev5-dogfood-20261006)
<<<
RELATIONS:
- TYPE: Parent
  VALUE: SEC-FIX
- TYPE: Parent
  VALUE: CM-3
  ROLE: ConformsTo

[REQUIREMENT]
UID: FIX-SUCC-2HOP.1
STATUS: Draft
TITLE: Two-hop succession with stale edge
STATEMENT: >>>
FIXTURE / TEST BED (not a product feature). Version .1 wording — superseded in-place when .2 activated. An edge intentionally still targets this superseded UID for stale-link / trace_suspect UX tests (FIX-SUSPECT-ON-CONTENT-N / FIX-SUCC-2HOP.1).
<<<
COMMENT: >>>
KIND: requirement
BASE_UID: FIX-SUCC-2HOP
VERSION_N: 1
priority: 30
iteration: iter-r0
security.catalog_ref: CM-3
security.verification_note: Succession immutability / change control (CM-3).
edge: ← uses from FIX-CONTRACT-DOC-NOCTX
in_scope_of_contract: Legacy intake (closed)
edge: → conforms_to to CM-3 (pin imprint=nist-800-53@rev5-dogfood-20261006)
<<<
RELATIONS:
- TYPE: Parent
  VALUE: SEC-FIX
- TYPE: Parent
  VALUE: CM-3
  ROLE: ConformsTo
- TYPE: Child
  VALUE: CONTRACT-contract-legacy-intake-closed
  ROLE: InScopeOf

[REQUIREMENT]
UID: FIX-SUCC-2HOP.2
STATUS: Active
TITLE: Two-hop succession with stale edge
STATEMENT: >>>
FIXTURE / TEST BED (not a product feature). Active successor after two superseded hops (.0 → .1 → .2). Implementers must resolve lineage to .2 while detecting edges that still point at superseded UIDs (FIX-SUCC-2HOP.1) as trace_suspect (ARCH-SUSPECT).
<<<
COMMENT: >>>
KIND: requirement
BASE_UID: FIX-SUCC-2HOP
VERSION_N: 2
priority: 30
iteration: iter-r1
security.catalog_ref: CM-3
security.verification_note: Succession immutability / change control (CM-3).
in_scope_of_contract: ReqALM product (build)
delivered_by_release: R1-core-ALM
edge: → conforms_to to CM-3 (pin imprint=nist-800-53@rev5-dogfood-20261006)
<<<
RELATIONS:
- TYPE: Parent
  VALUE: SEC-FIX
- TYPE: Parent
  VALUE: ARCH-VER-SUCC
  ROLE: Refines
- TYPE: Parent
  VALUE: CM-3
  ROLE: ConformsTo
- TYPE: Child
  VALUE: CONTRACT-ctr-reqalm-product
  ROLE: InScopeOf
- TYPE: Child
  VALUE: RELEASE-rel-r1-core-alm
  ROLE: Delivers

[REQUIREMENT]
UID: FIX-CONTRACT-DOC-NOCTX
STATUS: Active
TITLE: Doc view no-context = {A01,A02}
STATEMENT: >>>
FIXTURE / TEST BED. Document view from a contract with include-context-parents=false must return exactly the in_scope_of version UID set (no ancestor section/requirement UIDs outside the junction). Expected set for contract-fixture-doc-walk: {A01, A02}. Catalog items (AC-3) are not version UIDs and are excluded. Pairs ARCH-CONTRACT-DOC pattern.
<<<
COMMENT: >>>
KIND: requirement
BASE_UID: FIX-CONTRACT-DOC-NOCTX
VERSION_N: 0
rbac_op: contract:document:view
priority: 25
iteration: iter-r1
security.catalog_ref: REQALM-SEC-SCOPE
security.verification_note: UID set equality: view == in_scope_of when context parents off.
in_scope_of_contract: ReqALM product (build)
edge: → conforms_to to AC-3 (pin imprint=nist-800-53@rev5-dogfood-20261006)
<<<
RELATIONS:
- TYPE: Parent
  VALUE: SEC-FIX
- TYPE: Parent
  VALUE: FIX-SUCC-2HOP.1
  ROLE: Uses
- TYPE: Parent
  VALUE: ARCH-CONTRACT-DOC
  ROLE: Refines
- TYPE: Parent
  VALUE: AC-3
  ROLE: ConformsTo
- TYPE: Child
  VALUE: CONTRACT-ctr-reqalm-product
  ROLE: InScopeOf

[REQUIREMENT]
UID: FIX-CONTRACT-DOC-CTX
STATUS: Active
TITLE: Doc view + parents = {A01,A02} ∪ section walk
STATEMENT: >>>
FIXTURE / TEST BED. Document view with include-context-parents=true returns in_scope_of UIDs plus walked parent line versions (section ancestors) for readability. Expected: in_scope_of ∪ parent-walk(A01,A02) including SEC-IA / SEC-SEC section UIDs — NOT catalog item AC-3. Pairs ARCH-CONTRACT-DOC pattern.
<<<
COMMENT: >>>
KIND: requirement
BASE_UID: FIX-CONTRACT-DOC-CTX
VERSION_N: 0
rbac_op: contract:document:view
priority: 25
iteration: iter-r1
security.catalog_ref: REQALM-SEC-SCOPE
security.verification_note: UID set = in_scope_of ∪ context parents when toggle on.
in_scope_of_contract: ReqALM product (build)
edge: → conforms_to to AC-3 (pin imprint=nist-800-53@rev5-dogfood-20261006)
<<<
RELATIONS:
- TYPE: Parent
  VALUE: SEC-FIX
- TYPE: Parent
  VALUE: ARCH-CONTRACT-DOC
  ROLE: Refines
- TYPE: Parent
  VALUE: AC-3
  ROLE: ConformsTo
- TYPE: Child
  VALUE: CONTRACT-ctr-reqalm-product
  ROLE: InScopeOf

[REQUIREMENT]
UID: FIX-REL-SNAP
STATUS: Active
TITLE: Shipped release freeze + stale backlog UID
STATEMENT: >>>
FIXTURE / TEST BED (not a product feature). Assert R0-sequences (rel-r0-sequences) shipped
freeze is immutable — delivers list must not change after ship. Planned release
rel-r1-core-alm intentionally still lists obsolete UID ARCH-CONTRACT for stale-backlog UX
(implementers surface warning; do not auto-rewrite shipped snapshots).
<<<
COMMENT: >>>
KIND: requirement
BASE_UID: FIX-REL-SNAP
VERSION_N: 0
rbac_op: release:ship
priority: 25
iteration: iter-r1
security.catalog_ref: REQALM-SEC-AUDIT
security.verification_note: R0 freeze immutable; planned backlog may reference obsolete UIDs.
in_scope_of_contract: ReqALM product (build)
delivered_by_release: R1-core-ALM
edge: → conforms_to to CM-3 (pin imprint=nist-800-53@rev5-dogfood-20261006)
edge: → conforms_to to AU-12 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-6 (pin imprint=nist-800-53@rev5-dogfood-20261006)
<<<
RELATIONS:
- TYPE: Parent
  VALUE: SEC-FIX
- TYPE: Parent
  VALUE: ARCH-RELEASE-FREEZE
  ROLE: Refines
- TYPE: Parent
  VALUE: CM-3
  ROLE: ConformsTo
- TYPE: Parent
  VALUE: AU-12
  ROLE: ConformsTo
- TYPE: Parent
  VALUE: AU-2
  ROLE: ConformsTo
- TYPE: Parent
  VALUE: AU-3
  ROLE: ConformsTo
- TYPE: Parent
  VALUE: AU-6
  ROLE: ConformsTo
- TYPE: Child
  VALUE: CONTRACT-ctr-reqalm-product
  ROLE: InScopeOf
- TYPE: Child
  VALUE: RELEASE-rel-r1-core-alm
  ROLE: Delivers

[REQUIREMENT]
UID: FIX-ALLOW-CLIENT-CREATE
STATUS: Active
TITLE: Pat Client-Admin client:create allow
STATEMENT: >>>
FIXTURE / TEST BED (not a product feature). Identity pat-client-admin with client_grant
Client admin on raby-family performs client:create → HTTP 201 and an allow audit row
(action=client:create, outcome=allow). Demonstrates B01 happy path without inventing new product roles.
<<<
COMMENT: >>>
KIND: requirement
BASE_UID: FIX-ALLOW-CLIENT-CREATE
VERSION_N: 0
rbac_op: client:create
priority: 30
iteration: iter-r1
security.catalog_ref: AC-3
security.verification_note: Happy path for B01. Sample audit ae-allow-pat-client-create.
in_scope_of_contract: ReqALM product (build)
edge: → conforms_to to AC-2 (pin imprint=nist-800-53@rev5-dogfood-20261006)
edge: → conforms_to to AC-3 (pin imprint=nist-800-53@rev5-dogfood-20261006)
<<<
RELATIONS:
- TYPE: Parent
  VALUE: SEC-FIX
- TYPE: Parent
  VALUE: AC-2
  ROLE: ConformsTo
- TYPE: Parent
  VALUE: B01
  ROLE: Uses
- TYPE: Parent
  VALUE: AC-3
  ROLE: ConformsTo
- TYPE: Child
  VALUE: CONTRACT-ctr-reqalm-product
  ROLE: InScopeOf

[REQUIREMENT]
UID: FIX-ALLOW-STEWARD-UPDATE
STATUS: Active
TITLE: Morgan steward catalog:entry:update allow on project catalog
STATEMENT: >>>
FIXTURE / TEST BED (not a product feature). Identity morgan-steward with
catalog_steward_grants on cat-reqaml-security performs catalog:entry:update → 200 and allow audit.
Pairs H05; contrasts FIX-DENY-STEWARD-STANDARD on cat-nist-global.
<<<
COMMENT: >>>
KIND: requirement
BASE_UID: FIX-ALLOW-STEWARD-UPDATE
VERSION_N: 0
rbac_op: catalog:entry:update
priority: 30
iteration: iter-r1
security.catalog_ref: REQALM-SEC-CATALOG
security.verification_note: Happy path steward update on mutable project catalog. Sample ae-allow-morgan-steward-update.
in_scope_of_contract: ReqALM product (build)
edge: → conforms_to to AC-3 (pin imprint=nist-800-53@rev5-dogfood-20261006)
edge: → conforms_to to CM-5 (pin imprint=nist-800-53@rev5-dogfood-20261006)
<<<
RELATIONS:
- TYPE: Parent
  VALUE: SEC-FIX
- TYPE: Parent
  VALUE: H05
  ROLE: Uses
- TYPE: Parent
  VALUE: AC-3
  ROLE: ConformsTo
- TYPE: Parent
  VALUE: CM-5
  ROLE: ConformsTo
- TYPE: Child
  VALUE: CONTRACT-ctr-reqalm-product
  ROLE: InScopeOf

[REQUIREMENT]
UID: FIX-DENY-CLOSED-LINK
STATUS: Active
TITLE: Link to closed contract denied
STATEMENT: >>>
FIXTURE / TEST BED (not a product feature). Author attempts contract:link against
contract-legacy-intake-closed (status=closed) → 403/409 and deny audit. Closed contracts freeze
membership edits (pairs F03).
<<<
COMMENT: >>>
KIND: requirement
BASE_UID: FIX-DENY-CLOSED-LINK
VERSION_N: 0
rbac_op: contract:link
priority: 30
iteration: iter-r1
security.catalog_ref: AC-3
security.verification_note: AC-3 + CM-3 change control on closed contracts. Sample ae-deny-closed-link.
in_scope_of_contract: ReqALM product (build)
edge: → conforms_to to AC-3 (pin imprint=nist-800-53@rev5-dogfood-20261006)
edge: → conforms_to to CM-3 (pin imprint=nist-800-53@rev5-dogfood-20261006)
<<<
RELATIONS:
- TYPE: Parent
  VALUE: SEC-FIX
- TYPE: Parent
  VALUE: F03
  ROLE: Uses
- TYPE: Parent
  VALUE: AC-3
  ROLE: ConformsTo
- TYPE: Parent
  VALUE: CM-3
  ROLE: ConformsTo
- TYPE: Child
  VALUE: CONTRACT-ctr-reqalm-product
  ROLE: InScopeOf

[REQUIREMENT]
UID: FIX-DENY-SHIPPED-DELIVERS
STATUS: Active
TITLE: Mutate shipped release delivers denied
STATEMENT: >>>
FIXTURE / TEST BED (not a product feature). Release manager attempts release:membership
add/remove on R0-sequences (status=shipped) → 403/409 and deny audit. Shipped delivers are immutable
(pairs G03, ARCH-RELEASE-FREEZE, CM-3).
<<<
COMMENT: >>>
KIND: requirement
BASE_UID: FIX-DENY-SHIPPED-DELIVERS
VERSION_N: 0
rbac_op: release:membership
priority: 30
iteration: iter-r1
security.catalog_ref: CM-3
security.verification_note: CM-3 freeze. Sample ae-deny-shipped-delivers.
in_scope_of_contract: ReqALM product (build)
edge: → conforms_to to CM-3 (pin imprint=nist-800-53@rev5-dogfood-20261006)
<<<
RELATIONS:
- TYPE: Parent
  VALUE: SEC-FIX
- TYPE: Parent
  VALUE: CM-3
  ROLE: ConformsTo
- TYPE: Parent
  VALUE: G03
  ROLE: Uses
- TYPE: Child
  VALUE: CONTRACT-ctr-reqalm-product
  ROLE: InScopeOf

[REQUIREMENT]
UID: FIX-DENY-EDIT-ACTIVE
STATUS: Active
TITLE: Edit active version fields denied
STATEMENT: >>>
FIXTURE / TEST BED (not a product feature). Author attempts requirement:version:update_draft
on an active version (e.g. A01) → 403/409; must create successor instead (pairs D03, CM-3).
<<<
COMMENT: >>>
KIND: requirement
BASE_UID: FIX-DENY-EDIT-ACTIVE
VERSION_N: 0
rbac_op: requirement:version:update_draft
priority: 30
iteration: iter-r1
security.catalog_ref: CM-3
security.verification_note: CM-3 immutability of published versions. Sample ae-deny-edit-active.
in_scope_of_contract: ReqALM product (build)
edge: → conforms_to to CM-3 (pin imprint=nist-800-53@rev5-dogfood-20261006)
<<<
RELATIONS:
- TYPE: Parent
  VALUE: SEC-FIX
- TYPE: Parent
  VALUE: CM-3
  ROLE: ConformsTo
- TYPE: Parent
  VALUE: D03
  ROLE: Uses
- TYPE: Child
  VALUE: CONTRACT-ctr-reqalm-product
  ROLE: InScopeOf

[REQUIREMENT]
UID: FIX-ALLOW-SUCCEED
STATUS: Active
TITLE: Succeed .N; prior tip→superseded same txn
STATEMENT: >>>
FIXTURE / TEST BED. Author with active grant creates successor .N+1 via requirement:version:succeed / mint (mint_kind=content) on a line with an active tip → 201; in the SAME transaction the prior tip status becomes superseded (not left active). Demonstrates D02/D04 ≤1-active invariant. Contrast FIX-DENY-SECOND-ACTIVE.
<<<
COMMENT: >>>
KIND: requirement
BASE_UID: FIX-ALLOW-SUCCEED
VERSION_N: 0
rbac_op: requirement:version:succeed
priority: 30
iteration: iter-r1
security.catalog_ref: AC-3
security.verification_note: Happy path succession. Sample ae-allow-succeed.
in_scope_of_contract: ReqALM product (build)
edge: → conforms_to to AC-3 (pin imprint=nist-800-53@rev5-dogfood-20261006)
<<<
RELATIONS:
- TYPE: Parent
  VALUE: SEC-FIX
- TYPE: Parent
  VALUE: D02
  ROLE: Uses
- TYPE: Parent
  VALUE: AC-3
  ROLE: ConformsTo
- TYPE: Child
  VALUE: CONTRACT-ctr-reqalm-product
  ROLE: InScopeOf

[REQUIREMENT]
UID: FIX-COMPARE-2HOP
STATUS: Active
TITLE: Compare across two-hop succession
STATEMENT: >>>
FIXTURE / TEST BED (not a product feature). Reader compares FIX-SUCC-2HOP.0 vs
FIX-SUCC-2HOP.2 (two-hop succession). Field-level diff must surface statement changes across both hops
(pairs D07). Edge FIX-COMPARE-2HOP → D07 uses.
<<<
COMMENT: >>>
KIND: requirement
BASE_UID: FIX-COMPARE-2HOP
VERSION_N: 0
rbac_op: requirement:version:compare
priority: 30
iteration: iter-r1
security.catalog_ref: AC-3
security.verification_note: Uses D07 compare; lineage spans obsolete .0/.1 to active .2.
in_scope_of_contract: ReqALM product (build)
edge: → conforms_to to AC-3 (pin imprint=nist-800-53@rev5-dogfood-20261006)
<<<
RELATIONS:
- TYPE: Parent
  VALUE: SEC-FIX
- TYPE: Parent
  VALUE: D07
  ROLE: Uses
- TYPE: Parent
  VALUE: AC-3
  ROLE: ConformsTo
- TYPE: Child
  VALUE: CONTRACT-ctr-reqalm-product
  ROLE: InScopeOf

[REQUIREMENT]
UID: FIX-ALLOW-AUDIT-CLIENT
STATUS: Active
TITLE: Jordan Auditor audit:client:read allow
STATEMENT: >>>
FIXTURE / TEST BED (not a product feature). jordan-auditor with Auditor grant performs
audit:client:read on raby-family → 200 (pairs M02 and existing ae-jordan-audit-client-read).
<<<
COMMENT: >>>
KIND: requirement
BASE_UID: FIX-ALLOW-AUDIT-CLIENT
VERSION_N: 0
rbac_op: audit:client:read
priority: 30
iteration: iter-r1
security.catalog_ref: AU-6
security.verification_note: Auditor happy path. Existing ae-jordan-audit-client-read.
in_scope_of_contract: ReqALM product (build)
edge: → conforms_to to AU-6 (pin imprint=nist-800-53@rev5-dogfood-20261006)
<<<
RELATIONS:
- TYPE: Parent
  VALUE: SEC-FIX
- TYPE: Parent
  VALUE: M02
  ROLE: Uses
- TYPE: Parent
  VALUE: AU-6
  ROLE: ConformsTo
- TYPE: Child
  VALUE: CONTRACT-ctr-reqalm-product
  ROLE: InScopeOf

[REQUIREMENT]
UID: FIX-DENY-AUDIT-CROSS-CLIENT
STATUS: Active
TITLE: Auditor denied cross-client audit read
STATEMENT: >>>
FIXTURE / TEST BED (not a product feature). jordan-auditor attempts audit:client:read
while effectively scoped/requesting other-family → 403 and deny audit. Auditor role does not pierce
client isolation (pairs FIX-DENY-CROSS-CLIENT, M02).
<<<
COMMENT: >>>
KIND: requirement
BASE_UID: FIX-DENY-AUDIT-CROSS-CLIENT
VERSION_N: 0
rbac_op: audit:client:read
priority: 30
iteration: iter-r1
security.catalog_ref: AC-3
security.verification_note: Cross-client audit isolation. Sample ae-deny-audit-cross-client.
in_scope_of_contract: ReqALM product (build)
edge: → conforms_to to AC-3 (pin imprint=nist-800-53@rev5-dogfood-20261006)
<<<
RELATIONS:
- TYPE: Parent
  VALUE: SEC-FIX
- TYPE: Parent
  VALUE: M02
  ROLE: Uses
- TYPE: Parent
  VALUE: AC-3
  ROLE: ConformsTo
- TYPE: Child
  VALUE: CONTRACT-ctr-reqalm-product
  ROLE: InScopeOf

[REQUIREMENT]
UID: FIX-EXPORT-L02-GOLDEN
STATUS: Active
TITLE: Export golden UID set {A01,A02} (no AC-3)
STATEMENT: >>>
FIXTURE / TEST BED. Exporting contract-fixture-doc-walk with context parents off must emit exactly UID set {A01, A02} (same as in_scope_of). Golden: seed/fixtures/L02-contract-fixture-doc-walk.uids.txt. AC-3 is a catalog pin, not a version UID — must NOT appear in in_scope_of or the golden set. Pairs L02 and FIX-CONTRACT-DOC-NOCTX.
<<<
COMMENT: >>>
KIND: requirement
BASE_UID: FIX-EXPORT-L02-GOLDEN
VERSION_N: 0
rbac_op: io:export:strictdoc
priority: 30
iteration: iter-r1
security.catalog_ref: AC-3
security.verification_note: Golden UID set equality for L02 export of contract-fixture-doc-walk (context off).
in_scope_of_contract: ReqALM product (build)
edge: → conforms_to to AC-3 (pin imprint=nist-800-53@rev5-dogfood-20261006)
<<<
RELATIONS:
- TYPE: Parent
  VALUE: SEC-FIX
- TYPE: Parent
  VALUE: L02
  ROLE: Uses
- TYPE: Parent
  VALUE: AC-3
  ROLE: ConformsTo
- TYPE: Child
  VALUE: CONTRACT-ctr-reqalm-product
  ROLE: InScopeOf

[REQUIREMENT]
UID: FIX-DENY-NOOP-SUCCESSOR
STATUS: Active
TITLE: ALIGNED→FIX-DENY-NOOP-CONTENT (content mint noop deny)
STATEMENT: >>>
FIXTURE / TEST BED — ALIGNED / SUPERSEDED by FIX-DENY-NOOP-CONTENT for mint_kind=content. Retained as alias pointer: same-hash content mint deny via gate-noop-successor-block. Prefer FIX-DENY-NOOP-CONTENT in new tests. status/pin/security_meta mints are exempt (ARCH-MINT-KIND).
<<<
COMMENT: >>>
KIND: requirement
BASE_UID: FIX-DENY-NOOP-SUCCESSOR
VERSION_N: 0
rbac_op: requirement:version:mint
priority: 20
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: FIX-DENY-REVERT-NON-LATEST
STATUS: Active
TITLE: Non-latest change-set revert denied (unless abandon suffix)
STATEMENT: >>>
FIXTURE / TEST BED (not a product feature). Authorized actor attempts changeset:revert on a closed change set that is NOT the latest on the project stack while later sets remain non-abandoned (sample: revert cs-stack-older while cs-stack-newer is still closed tip) → expect HTTP 403/409 and audit_events row (action=changeset:revert, outcome=deny, gate-revert-latest-only). Contrast: revert of cs-stack-newer (latest) allowed; or abandon cs-stack-older AND cs-stack-newer then unwind. Pairs ARCH-CHANGESET-CONFLICT / M07.
<<<
COMMENT: >>>
KIND: requirement
BASE_UID: FIX-DENY-REVERT-NON-LATEST
VERSION_N: 0
rbac_op: changeset:revert
priority: 20
iteration: iter-r1
security.catalog_ref: AU-2
security.verification_note: AU-2/3/12 revert / change-set audit.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: FIX-SAMPLE-WF-REQ
STATUS: Active
TITLE: Sample client sys-req line with ApprovalRecord + Satisfies target
STATEMENT: >>>
SAMPLE / FIXTURE: client system requirement line for workflow path demo. ApprovalRecord ar-wf-sample-req approved; head version active; Satisfies target for FIX-SAMPLE-WF-CAP.
<<<
COMMENT: >>>
KIND: requirement
BASE_UID: FIX-SAMPLE-WF-REQ
VERSION_N: 0
priority: 20
iteration: iter-r1
security.catalog_ref: AC-3
security.verification_note: AC-3 access enforcement; AU-2/3/12 where mutating.
edge: ← satisfies from FIX-SAMPLE-WF-CAP
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: FIX-SAMPLE-WF-CAP
STATUS: Active
TITLE: Sample capability created with Satisfies + ApprovalRecord
STATEMENT: >>>
SAMPLE / FIXTURE: CapabilityLine created with Satisfies→FIX-SAMPLE-WF-REQ in the same mutation (no orphan). ApprovalRecord ar-wf-sample-cap approved as solution (ARCH-CAP-APPROVE).
<<<
COMMENT: >>>
KIND: capability
BASE_UID: FIX-SAMPLE-WF-CAP
VERSION_N: 0
priority: 20
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: FIX-SAMPLE-WF-REQ
  ROLE: Satisfies
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: FIX-ALLOW-PIN-MIGRATE-MINT
STATUS: Active
TITLE: Allow pin-only .N mint (exempt from content noop)
STATEMENT: >>>
FIXTURE / TEST BED. Author/Security performs requirement:version:mint with mint_kind=pin (locked ConformsTo migrate successor) where statement_hash equals prior tip → expect HTTP 201. gate-noop-successor-block does NOT deny. Line ApprovalRecord clears; locked migrate also requires gate_signoff (AO/Security) then re-approve (ARCH-MINT-KIND / ARCH-GATE-SIGNOFF / ARCH-CAT-MIGRATE).
<<<
COMMENT: >>>
KIND: requirement
BASE_UID: FIX-ALLOW-PIN-MIGRATE-MINT
VERSION_N: 0
rbac_op: requirement:version:mint
priority: 20
iteration: iter-r1
security.catalog_ref: CM-3
security.verification_note: CM-3 change control; mint kinds / succession.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-MINT-KIND
  ROLE: Uses
- TYPE: Child
  VALUE: CONTRACT-ctr-reqalm-product
  ROLE: InScopeOf

[REQUIREMENT]
UID: FIX-DENY-NOOP-CONTENT
STATUS: Active
TITLE: Deny content mint when statement_hash equals head
STATEMENT: >>>
FIXTURE / TEST BED. Author attempts requirement:version:mint with mint_kind=content and statement_hash equal to the current head hash → expect HTTP 403/409 and audit outcome=deny (gate-noop-successor-block / ARCH-SUCCESSION-HASH / ARCH-MINT-KIND). Replaces/aligns FIX-DENY-NOOP-SUCCESSOR for content mints. Contrast status/pin/security_meta mints which are exempt from this gate.
<<<
COMMENT: >>>
KIND: requirement
BASE_UID: FIX-DENY-NOOP-CONTENT
VERSION_N: 0
rbac_op: requirement:version:mint
priority: 20
iteration: iter-r1
security.catalog_ref: CM-3
security.verification_note: CM-3 change control; mint kinds / succession.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-SUCCESSION-HASH
  ROLE: Uses
- TYPE: Parent
  VALUE: ARCH-MINT-KIND
  ROLE: Uses
- TYPE: Child
  VALUE: CONTRACT-ctr-reqalm-product
  ROLE: InScopeOf
- TYPE: Child
  VALUE: RELEASE-rel-r1-core-alm
  ROLE: Delivers

[REQUIREMENT]
UID: FIX-ALLOW-STATUS-SUPERSEDE
STATUS: Active
TITLE: Allow in-place superseded / status-only terminal
STATEMENT: >>>
FIXTURE / TEST BED. (1) D04 activate of a new tip sets the prior active version status to superseded IN PLACE in the same transaction (not a new version). (2) Terminal obsolete/withdraw WITHOUT a replacement tip may be an in-place status change, OR a status-only .N (mint_kind=status) exempt from content no-op and that does NOT clear ApprovalRecord. Expect allow + audit. Pairs ARCH-VER / D05 / ARCH-MINT-KIND.
<<<
COMMENT: >>>
KIND: requirement
BASE_UID: FIX-ALLOW-STATUS-SUPERSEDE
VERSION_N: 0
rbac_op: requirement:version:activate
priority: 20
iteration: iter-r1
security.catalog_ref: CM-3
security.verification_note: CM-3 change control; mint kinds / succession.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-VER
  ROLE: Uses
- TYPE: Child
  VALUE: CONTRACT-ctr-reqalm-product
  ROLE: InScopeOf

[REQUIREMENT]
UID: FIX-DENY-SECOND-ACTIVE
STATUS: Active
TITLE: Deny second active tip on same line
STATEMENT: >>>
FIXTURE / TEST BED. Attempt to leave two versions of the same line with status=active (e.g. succeed without superseding prior tip, or activate a second tip while prior remains active) → expect HTTP 403/409 and audit outcome=deny. Invariant: ≤1 active per line (ARCH-VER-SUCC / FIX-ALLOW-SUCCEED rewrite).
<<<
COMMENT: >>>
KIND: requirement
BASE_UID: FIX-DENY-SECOND-ACTIVE
VERSION_N: 0
rbac_op: requirement:version:activate
priority: 20
iteration: iter-r1
security.catalog_ref: CM-3
security.verification_note: CM-3 change control; mint kinds / succession.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-VER-SUCC
  ROLE: Uses
- TYPE: Child
  VALUE: CONTRACT-ctr-reqalm-product
  ROLE: InScopeOf
- TYPE: Child
  VALUE: RELEASE-rel-r1-core-alm
  ROLE: Delivers

[REQUIREMENT]
UID: FIX-PLANNING-BLOCKED-AFTER-CONTENT-N
STATUS: Active
TITLE: planning_blocked after content .N until re-approve
STATEMENT: >>>
FIXTURE / TEST BED. After a content mint_kind=.N clears ApprovalRecord, the line is planning_blocked until re-approve. Priority/grooming/iteration VALUES are RETAINED but D08 (and other profile planning gates) still DENY mutate while blocked/unapproved. Contract in_scope_of and release delivers membership are NOT auto-dropped — marked suspect (trace_suspect) instead. Expect priority mutate deny + planning_blocked=true + membership retained.
<<<
COMMENT: >>>
KIND: requirement
BASE_UID: FIX-PLANNING-BLOCKED-AFTER-CONTENT-N
VERSION_N: 0
rbac_op: requirement:version:priority
priority: 20
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-SUCCESSION-HASH
  ROLE: Uses
- TYPE: Child
  VALUE: CONTRACT-ctr-reqalm-product
  ROLE: InScopeOf
- TYPE: Child
  VALUE: RELEASE-rel-r1-core-alm
  ROLE: Delivers

[REQUIREMENT]
UID: FIX-GRANDFATHER-SEED-APPROVED
STATUS: Active
TITLE: Bootstrap imported_approved / seed ApprovalRecords
STATEMENT: >>>
FIXTURE / TEST BED. Bootstrap/import (L01) and dogfood seed may mint ApprovalRecord status=imported_approved (or seed approved records) for prioritized lines so load does not fail gate-line-approved. Grandfather is explicit audit-visible policy — not silent bypass. Contrast unapproved FIX-SAMPLE-UNAPPROVED which still denies D08.
<<<
COMMENT: >>>
KIND: requirement
BASE_UID: FIX-GRANDFATHER-SEED-APPROVED
VERSION_N: 0
rbac_op: requirement:line:approve
priority: 20
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: FIX-SUSPECT-ON-CONTENT-N
STATUS: Active
TITLE: Content .N marks inbound traces suspect
STATEMENT: >>>
FIXTURE / TEST BED. Content .N on FIX-SUCC-2HOP (or any line) marks inbound edges/junctions that still point at prior version UIDs as trace_suspect. Seed bed: uses edge FIX-CONTRACT-DOC-NOCTX → FIX-SUCC-2HOP.1 already targets a superseded UID — expect trace_suspect=true after content succession (ARCH-SUSPECT).
<<<
COMMENT: >>>
KIND: requirement
BASE_UID: FIX-SUSPECT-ON-CONTENT-N
VERSION_N: 0
rbac_op: requirement:version:mint
priority: 20
iteration: iter-r1
security.catalog_ref: AU-2
security.verification_note: AU-2/3/12 workflow / approval / suspect audit.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-SUSPECT
  ROLE: Uses
- TYPE: Child
  VALUE: CONTRACT-ctr-reqalm-product
  ROLE: InScopeOf
- TYPE: Child
  VALUE: RELEASE-rel-r1-core-alm
  ROLE: Delivers

[REQUIREMENT]
UID: FIX-ALLOW-SUSPECT-CARRY
STATUS: Active
TITLE: Allow suspect carry-forward to new tip
STATEMENT: >>>
FIXTURE / TEST BED. Author (Satisfies/refines/uses) or Author+Release mgr (contract/release) carries a suspect edge/junction forward to the new tip → expect 200, trace_suspect cleared, audit reaction=carry.
<<<
COMMENT: >>>
KIND: requirement
BASE_UID: FIX-ALLOW-SUSPECT-CARRY
VERSION_N: 0
rbac_op: trace:suspect:carry
priority: 20
iteration: iter-r1
security.catalog_ref: AU-2
security.verification_note: AU-2/3/12 workflow / approval / suspect audit.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-SUSPECT-QUEUE
  ROLE: Uses
- TYPE: Child
  VALUE: CONTRACT-ctr-reqalm-product
  ROLE: InScopeOf

[REQUIREMENT]
UID: FIX-ALLOW-SUSPECT-KEEP-PINNED
STATUS: Active
TITLE: Allow keep-pinned on suspect edge
STATEMENT: >>>
FIXTURE / TEST BED. Authorized actor keeps a suspect edge pinned at the old version UID → expect 200, trace_suspect cleared with keep_pinned acknowledgment, audit reaction=keep_pinned.
<<<
COMMENT: >>>
KIND: requirement
BASE_UID: FIX-ALLOW-SUSPECT-KEEP-PINNED
VERSION_N: 0
rbac_op: trace:suspect:keep_pinned
priority: 20
iteration: iter-r1
security.catalog_ref: AU-2
security.verification_note: AU-2/3/12 workflow / approval / suspect audit.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-SUSPECT-QUEUE
  ROLE: Uses
- TYPE: Child
  VALUE: CONTRACT-ctr-reqalm-product
  ROLE: InScopeOf

[REQUIREMENT]
UID: FIX-ALLOW-SUSPECT-DROP
STATUS: Active
TITLE: Allow drop of suspect edge/junction
STATEMENT: >>>
FIXTURE / TEST BED. Authorized actor drops a suspect edge or contract/release junction → expect 200, membership/edge removed, audit reaction=drop.
<<<
COMMENT: >>>
KIND: requirement
BASE_UID: FIX-ALLOW-SUSPECT-DROP
VERSION_N: 0
rbac_op: trace:suspect:drop
priority: 20
iteration: iter-r1
security.catalog_ref: AU-2
security.verification_note: AU-2/3/12 workflow / approval / suspect audit.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-SUSPECT-QUEUE
  ROLE: Uses
- TYPE: Child
  VALUE: CONTRACT-ctr-reqalm-product
  ROLE: InScopeOf

[REQUIREMENT]
UID: FIX-DENY-SHIP-WITH-OPEN-SUSPECT
STATUS: Active
TITLE: Optional profile gate: deny ship with open suspects
STATEMENT: >>>
FIXTURE / TEST BED (optional profile gate gate-no-open-suspect). When profile enables the gate, G05 ship with any open trace_suspect on delivers (or related edges in scope) → expect 403/409 deny. Commercial default may leave this gate disabled; DoD/cyber example may enable it.
<<<
COMMENT: >>>
KIND: requirement
BASE_UID: FIX-DENY-SHIP-WITH-OPEN-SUSPECT
VERSION_N: 0
rbac_op: release:ship
priority: 20
iteration: iter-r1
security.catalog_ref: AU-2
security.verification_note: AU-2/3/12 workflow / approval / suspect audit.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-SUSPECT
  ROLE: Uses
- TYPE: Child
  VALUE: CONTRACT-ctr-reqalm-product
  ROLE: InScopeOf

[REQUIREMENT]
UID: FIX-DENY-AUTHOR-PIN-APPLY
STATUS: Active
TITLE: Deny Author applying ConformsTo pin
STATEMENT: >>>
FIXTURE / TEST BED. Author attempts catalog:pin:apply (or edge:create:conforms_to apply path) without conforms_to_applicator RoleBinding → expect 403 and audit deny (FIX-DENY-AUTHOR-PIN-APPLY). Author may only request (catalog:pin:request). Tree wins over E02/H06/H10 prior wording.
<<<
COMMENT: >>>
KIND: requirement
BASE_UID: FIX-DENY-AUTHOR-PIN-APPLY
VERSION_N: 0
rbac_op: catalog:pin:apply
priority: 20
iteration: iter-r1
security.catalog_ref: REQALM-SEC-CATALOG
security.verification_note: Catalog/ConformsTo authority; imprint pins. AC-3/CM-5.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: E02
  ROLE: Uses
- TYPE: Child
  VALUE: CONTRACT-ctr-reqalm-product
  ROLE: InScopeOf
- TYPE: Child
  VALUE: RELEASE-rel-r1-core-alm
  ROLE: Delivers

[REQUIREMENT]
UID: FIX-ALLOW-PIN-REQUEST
STATUS: Active
TITLE: Allow Author conformance_pin_request
STATEMENT: >>>
FIXTURE / TEST BED. Author creates conformance_pin_request (ops catalog:pin:request) → expect 201 and audit allow. Request waits for Security (standards) or Steward (non-standard) apply/deny. Profile slot conforms_to_applicator may bind Author on commercial profiles.
<<<
COMMENT: >>>
KIND: requirement
BASE_UID: FIX-ALLOW-PIN-REQUEST
VERSION_N: 0
rbac_op: catalog:pin:request
priority: 20
iteration: iter-r1
security.catalog_ref: REQALM-SEC-CATALOG
security.verification_note: Catalog/ConformsTo authority; imprint pins. AC-3/CM-5.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: E02
  ROLE: Uses
- TYPE: Child
  VALUE: CONTRACT-ctr-reqalm-product
  ROLE: InScopeOf
- TYPE: Child
  VALUE: RELEASE-rel-r1-core-alm
  ROLE: Delivers

[REQUIREMENT]
UID: FIX-ALLOW-SECURITY-PIN-APPLY
STATUS: Active
TITLE: Allow Security/Steward pin apply
STATEMENT: >>>
FIXTURE / TEST BED. Security (standards imprint) or Steward (non-standard) with conforms_to_applicator slot applies (catalog:pin:apply) or denies a conformance_pin_request → expect 200 and audit. AO is approve-only on locked migrate (gate_signoff), never free pin edit.
<<<
COMMENT: >>>
KIND: requirement
BASE_UID: FIX-ALLOW-SECURITY-PIN-APPLY
VERSION_N: 0
rbac_op: catalog:pin:apply
priority: 20
iteration: iter-r1
security.catalog_ref: REQALM-SEC-CATALOG
security.verification_note: Catalog/ConformsTo authority; imprint pins. AC-3/CM-5.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: E02
  ROLE: Uses
- TYPE: Child
  VALUE: CONTRACT-ctr-reqalm-product
  ROLE: InScopeOf
- TYPE: Child
  VALUE: RELEASE-rel-r1-core-alm
  ROLE: Delivers

[REQUIREMENT]
UID: FIX-DENY-APPROVE-WITHOUT-SLOT
STATUS: Active
TITLE: Deny approve when actor misses RoleBinding slot
STATEMENT: >>>
FIXTURE / TEST BED. Actor without matching RoleBinding for gate-approver-slot attempts requirement:line:approve or capability:line:approve → expect 403 and audit deny. Approve hooks evaluate gates_before including gate-approver-slot (P0-4).
<<<
COMMENT: >>>
KIND: requirement
BASE_UID: FIX-DENY-APPROVE-WITHOUT-SLOT
VERSION_N: 0
rbac_op: requirement:line:approve
priority: 20
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: D12
  ROLE: Uses
- TYPE: Child
  VALUE: CONTRACT-ctr-reqalm-product
  ROLE: InScopeOf
- TYPE: Child
  VALUE: RELEASE-rel-r1-core-alm
  ROLE: Delivers

[REQUIREMENT]
UID: FIX-ALLOW-APPROVE-LINE
STATUS: Active
TITLE: Allow approve when actor matches slot
STATEMENT: >>>
FIXTURE / TEST BED. Actor matching stakeholder (or solution_approver) RoleBinding performs requirement:line:approve on an eligible line → expect 200, ApprovalRecord written, audit allow. Pairs D12 / UI-APPROVE-LINE / gate-approver-slot.
<<<
COMMENT: >>>
KIND: requirement
BASE_UID: FIX-ALLOW-APPROVE-LINE
VERSION_N: 0
rbac_op: requirement:line:approve
priority: 20
iteration: iter-r1
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: D12
  ROLE: Uses
- TYPE: Child
  VALUE: CONTRACT-ctr-reqalm-product
  ROLE: InScopeOf
- TYPE: Child
  VALUE: RELEASE-rel-r1-core-alm
  ROLE: Delivers

[REQUIREMENT]
UID: FIX-DENY-SHIP-UNSIGNED
STATUS: Active
TITLE: Deny cyber ship until required slots signed
STATEMENT: >>>
FIXTURE / TEST BED. Release manager attempts G05 ship on a release with cyber_gate=true while gate-cyber-ship is enabled and required gate_signoff rows for security_signoff and/or ao_approve are missing → expect 403/409 deny (ARCH-GATE-SIGNOFF / ARCH-CYBER-GATE).
<<<
COMMENT: >>>
KIND: requirement
BASE_UID: FIX-DENY-SHIP-UNSIGNED
VERSION_N: 0
rbac_op: release:ship
priority: 20
iteration: iter-r1
security.catalog_ref: AU-2
security.verification_note: AU-2/3/12 workflow / approval / suspect audit.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-FIX
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-GATE-SIGNOFF
  ROLE: Uses
- TYPE: Child
  VALUE: CONTRACT-ctr-reqalm-product
  ROLE: InScopeOf
- TYPE: Child
  VALUE: RELEASE-rel-r1-core-alm
  ROLE: Delivers

[REQUIREMENT]
UID: FIX-ALLOW-DEVENV-SMOKE
STATUS: Active
TITLE: Fresh clone reaches healthy instance and seed loads
STATEMENT: >>>
FIXTURE / TEST BED (not a product feature). From a clean clone of the repo, following the documented clone-to-running sequence yields: Compose services healthy, API health/version OK (M04), and dogfood seed loaded (seed identities/grants/requirement fixtures queryable). Pairs ARCH-DEVENV-CLONE / ARCH-DEVENV-SEED / ARCH-DEVENV-HEALTH.
<<<
COMMENT: >>>
KIND: requirement
BASE_UID: FIX-ALLOW-DEVENV-SMOKE
VERSION_N: 0
priority: 20
iteration: iter-r1
security.catalog_ref: CM-6
security.verification_note: FIXTURE / TEST BED for developer environment smoke and prod-disable.
edge: ← satisfies from CAP-DEVENV-SMOKE
edge: ← satisfies from CAP-TEST-PNPM-GATE
edge: ← satisfies from CAP-DEVENV-SMOKE-COMPOSE-ISOLATION
in_scope_of_contract: ReqALM product (build)
delivered_by_release: PR #12 — devenv foundation
edge: → conforms_to to CM-2 (pin imprint=nist-800-53@rev5-dogfood-20261006)
<<<
RELATIONS:
- TYPE: Parent
  VALUE: SEC-FIX
- TYPE: Parent
  VALUE: ARCH-DEVENV-CLONE
  ROLE: Uses
- TYPE: Parent
  VALUE: ARCH-DEVENV-SEED
  ROLE: Uses
- TYPE: Parent
  VALUE: ARCH-DEVENV-HEALTH
  ROLE: Uses
- TYPE: Parent
  VALUE: M04
  ROLE: Uses
- TYPE: Parent
  VALUE: CM-2
  ROLE: ConformsTo
- TYPE: Child
  VALUE: CONTRACT-ctr-reqalm-product
  ROLE: InScopeOf
- TYPE: Child
  VALUE: RELEASE-rel-pr12-devenv-foundation
  ROLE: Delivers

[REQUIREMENT]
UID: FIX-DENY-DEVENV-PROD-LOGIN
STATUS: Draft
TITLE: No seeded dev accounts or default credentials in production
STATEMENT: >>>
FIXTURE / TEST BED (not a product feature). With a production build or production configuration, attempting the local/dev identity path (OIDC stub or dev-login) is denied or the route/config is absent → expect unauthorized/forbidden (or missing endpoint). Enterprise SSO (A01) remains the only sign-in path. Pairs ARCH-DEVENV-IDENTITY and REQAML-SEC-SSO.
<<<
COMMENT: >>>
KIND: requirement
BASE_UID: FIX-DENY-DEVENV-PROD-LOGIN
VERSION_N: 0
rbac_op: auth:signin
priority: 15
iteration: iter-r1
security.catalog_ref: AC-3
security.verification_note: AC-3: production builds must not accept the local-only identity path.
edge: ← refines from FIX-DENY-DEVENV-PROD-LOGIN.1
edge: → conforms_to to CM-7 (pin imprint=nist-800-53@rev5-dogfood-20261006)
edge: → conforms_to to V-222518 (pin imprint=asd-stig@v6r4)
<<<
RELATIONS:
- TYPE: Parent
  VALUE: SEC-FIX
- TYPE: Parent
  VALUE: ARCH-DEVENV-IDENTITY
  ROLE: Uses
- TYPE: Parent
  VALUE: A01
  ROLE: Uses
- TYPE: Parent
  VALUE: CM-7
  ROLE: ConformsTo
- TYPE: Parent
  VALUE: V-222518
  ROLE: ConformsTo

[REQUIREMENT]
UID: FIX-DENY-DEVENV-PROD-LOGIN.1
STATUS: Active
TITLE: No seeded dev accounts or default credentials in production
STATEMENT: >>>
FIXTURE / TEST BED (not a product feature). Production build or production configuration: (a) no seeded dev accounts exist, so logging in as a dev account (for example taylor-tester's dev local account) → generic invalid-credentials and an audit failure; (b) running the dev seed loader in production mode → refused (non-zero exit), no accounts created; (c) the startup self-check finds no default or seeded credentials, and fails startup if it does. Pairs ARCH-DEVENV-IDENTITY.1 and ARCH-CRED-POLICY.
<<<
COMMENT: >>>
KIND: requirement
BASE_UID: FIX-DENY-DEVENV-PROD-LOGIN
VERSION_N: 1
rbac_op: auth:local:signin
priority: 15
iteration: iter-r1
security.catalog_ref: CM-7
security.verification_note: CM-7; ASD V-222662 default passwords / V-222661 built-in accounts.
edge: ← satisfies from CAP-PROD-SELFCHECK
in_scope_of_contract: ReqALM product (build)
edge: → conforms_to to CM-7 (pin imprint=nist-800-53@rev5-dogfood-20261006)
edge: → conforms_to to V-222662 (pin imprint=asd-stig@v6r4)
edge: → conforms_to to V-222661 (pin imprint=asd-stig@v6r4)
<<<
RELATIONS:
- TYPE: Parent
  VALUE: SEC-FIX
- TYPE: Parent
  VALUE: ARCH-DEVENV-IDENTITY.1
  ROLE: Uses
- TYPE: Parent
  VALUE: A01
  ROLE: Uses
- TYPE: Parent
  VALUE: FIX-DENY-DEVENV-PROD-LOGIN
  ROLE: Refines
- TYPE: Parent
  VALUE: ARCH-CRED-POLICY
  ROLE: Uses
- TYPE: Parent
  VALUE: CM-7
  ROLE: ConformsTo
- TYPE: Parent
  VALUE: V-222662
  ROLE: ConformsTo
- TYPE: Parent
  VALUE: V-222661
  ROLE: ConformsTo
- TYPE: Child
  VALUE: CONTRACT-ctr-reqalm-product
  ROLE: InScopeOf

[REQUIREMENT]
UID: FIX-ALLOW-DEVENV-SEED-IDEMPOTENT
STATUS: Active
TITLE: Re-run migrations and dogfood seed is idempotent
STATEMENT: >>>
FIXTURE / TEST BED (not a product feature). After a successful first migration + dogfood seed load, re-running the same migrate/seed command (or Compose first-start hook) succeeds without duplicate key errors and leaves fixture row counts unchanged. Pairs ARCH-DEVENV-SEED.
<<<
COMMENT: >>>
KIND: requirement
BASE_UID: FIX-ALLOW-DEVENV-SEED-IDEMPOTENT
VERSION_N: 0
priority: 25
iteration: iter-r1
security.catalog_ref: CM-6
security.verification_note: FIXTURE / TEST BED for developer environment smoke and prod-disable.
edge: ← satisfies from CAP-DEVENV-MIGRATE-SEED
edge: ← satisfies from CAP-DEVENV-SMOKE
edge: ← satisfies from CAP-DEVENV-SEED-RESET
in_scope_of_contract: ReqALM product (build)
delivered_by_release: PR #12 — devenv foundation
edge: → conforms_to to CM-6 (pin imprint=nist-800-53@rev5-dogfood-20261006)
<<<
RELATIONS:
- TYPE: Parent
  VALUE: SEC-FIX
- TYPE: Parent
  VALUE: ARCH-DEVENV-SEED
  ROLE: Uses
- TYPE: Parent
  VALUE: CM-6
  ROLE: ConformsTo
- TYPE: Child
  VALUE: CONTRACT-ctr-reqalm-product
  ROLE: InScopeOf
- TYPE: Child
  VALUE: RELEASE-rel-pr12-devenv-foundation
  ROLE: Delivers

[REQUIREMENT]
UID: FIX-ALLOW-MCP-OAUTH-PKCE
STATUS: Active
TITLE: MCP client authorizes via discovery + PKCE; audience-bound tool call
STATEMENT: >>>
FIXTURE / TEST BED (not a product feature). MCP host (as alex-author) calls the MCP server without a token → 401 + WWW-Authenticate resource_metadata. It fetches PRM, then AS metadata (issuer match, S256 advertised), authorizes with S256 + resource=MCP URI, and exchanges code + verifier + resource for an aud=MCP access token plus a rotating refresh token. The tool update_draft then succeeds (200) after the audience check and RBAC.
<<<
COMMENT: >>>
KIND: requirement
BASE_UID: FIX-ALLOW-MCP-OAUTH-PKCE
VERSION_N: 0
rbac_op: auth:oauth:authorize, requirement:version:update_draft
priority: 10
iteration: iter-r1
security.catalog_ref: IA-2
security.verification_note: Happy path for ARCH-AUTH-* / MCP spec.
in_scope_of_contract: ReqALM product (build)
edge: → conforms_to to IA-2 (pin imprint=nist-800-53@rev5-dogfood-20261006)
<<<
RELATIONS:
- TYPE: Parent
  VALUE: SEC-FIX
- TYPE: Parent
  VALUE: ARCH-AUTH-METADATA
  ROLE: Uses
- TYPE: Parent
  VALUE: ARCH-AUTH-PKCE
  ROLE: Uses
- TYPE: Parent
  VALUE: ARCH-AUTH-AUDIENCE
  ROLE: Uses
- TYPE: Parent
  VALUE: MC02
  ROLE: Uses
- TYPE: Parent
  VALUE: IA-2
  ROLE: ConformsTo
- TYPE: Child
  VALUE: CONTRACT-ctr-reqalm-product
  ROLE: InScopeOf

[REQUIREMENT]
UID: FIX-DENY-PKCE-PLAIN
STATUS: Active
TITLE: Deny authorize with plain or missing PKCE
STATEMENT: >>>
FIXTURE / TEST BED (not a product feature). Authorize request with code_challenge_method=plain, or no code_challenge → expect 400 invalid_request, no authorization code issued, audit deny.
<<<
COMMENT: >>>
KIND: requirement
BASE_UID: FIX-DENY-PKCE-PLAIN
VERSION_N: 0
rbac_op: auth:oauth:authorize
priority: 10
iteration: iter-r1
security.catalog_ref: IA-2.8
security.verification_note: Pairs ARCH-AUTH-PKCE; ASD V-222530.
in_scope_of_contract: ReqALM product (build)
edge: → conforms_to to IA-2.8 (pin imprint=nist-800-53@rev5-dogfood-20261006)
edge: → conforms_to to V-222530 (pin imprint=asd-stig@v6r4)
<<<
RELATIONS:
- TYPE: Parent
  VALUE: SEC-FIX
- TYPE: Parent
  VALUE: ARCH-AUTH-PKCE
  ROLE: Uses
- TYPE: Parent
  VALUE: IA-2.8
  ROLE: ConformsTo
- TYPE: Parent
  VALUE: V-222530
  ROLE: ConformsTo
- TYPE: Child
  VALUE: CONTRACT-ctr-reqalm-product
  ROLE: InScopeOf

[REQUIREMENT]
UID: FIX-DENY-MCP-WRONG-AUDIENCE
STATUS: Active
TITLE: Deny token with wrong audience at MCP server / API
STATEMENT: >>>
FIXTURE / TEST BED (not a product feature). aud=API access token presented to the MCP server → 401 invalid_token + WWW-Authenticate resource_metadata. An aud=MCP token presented to the API → 401. No tool or business call runs.
<<<
COMMENT: >>>
KIND: requirement
BASE_UID: FIX-DENY-MCP-WRONG-AUDIENCE
VERSION_N: 0
rbac_op: auth:token:validate
priority: 10
iteration: iter-r1
security.catalog_ref: SC-23
security.verification_note: Pairs ARCH-AUTH-AUDIENCE.
in_scope_of_contract: ReqALM product (build)
edge: → conforms_to to SC-23 (pin imprint=nist-800-53@rev5-dogfood-20261006)
<<<
RELATIONS:
- TYPE: Parent
  VALUE: SEC-FIX
- TYPE: Parent
  VALUE: ARCH-AUTH-AUDIENCE
  ROLE: Uses
- TYPE: Parent
  VALUE: ARCH-AUTH-METADATA
  ROLE: Uses
- TYPE: Parent
  VALUE: SC-23
  ROLE: ConformsTo
- TYPE: Child
  VALUE: CONTRACT-ctr-reqalm-product
  ROLE: InScopeOf

[REQUIREMENT]
UID: FIX-DENY-UPSTREAM-TOKEN-AT-API
STATUS: Active
TITLE: Deny upstream IdP token presented directly to API/MCP
STATEMENT: >>>
FIXTURE / TEST BED (not a product feature). A token minted by the upstream enterprise IdP, presented directly to the API or MCP server → 401 (issuer not trusted). Only internal-AS tokens are accepted.
<<<
COMMENT: >>>
KIND: requirement
BASE_UID: FIX-DENY-UPSTREAM-TOKEN-AT-API
VERSION_N: 0
rbac_op: auth:token:validate
priority: 15
iteration: iter-r1
security.catalog_ref: IA-2
security.verification_note: Pairs ARCH-AUTH-FEDERATION: no separate token path.
in_scope_of_contract: ReqALM product (build)
edge: → conforms_to to IA-2 (pin imprint=nist-800-53@rev5-dogfood-20261006)
<<<
RELATIONS:
- TYPE: Parent
  VALUE: SEC-FIX
- TYPE: Parent
  VALUE: ARCH-AUTH-FEDERATION
  ROLE: Uses
- TYPE: Parent
  VALUE: IA-2
  ROLE: ConformsTo
- TYPE: Child
  VALUE: CONTRACT-ctr-reqalm-product
  ROLE: InScopeOf

[REQUIREMENT]
UID: FIX-DENY-REFRESH-REUSE
STATUS: Active
TITLE: Deny reuse of a rotated refresh token; revoke family
STATEMENT: >>>
FIXTURE / TEST BED (not a product feature). Refresh token R1 rotated to R2; presenting R1 again → 400 invalid_grant. R2 and its derived access tokens are revoked (token family), and an audit row records reuse detection.
<<<
COMMENT: >>>
KIND: requirement
BASE_UID: FIX-DENY-REFRESH-REUSE
VERSION_N: 0
rbac_op: auth:oauth:token
priority: 10
iteration: iter-r1
security.catalog_ref: SC-23
security.verification_note: Pairs ARCH-AUTH-REFRESH.
in_scope_of_contract: ReqALM product (build)
edge: → conforms_to to SC-23 (pin imprint=nist-800-53@rev5-dogfood-20261006)
<<<
RELATIONS:
- TYPE: Parent
  VALUE: SEC-FIX
- TYPE: Parent
  VALUE: ARCH-AUTH-REFRESH
  ROLE: Uses
- TYPE: Parent
  VALUE: SC-23
  ROLE: ConformsTo
- TYPE: Child
  VALUE: CONTRACT-ctr-reqalm-product
  ROLE: InScopeOf

[REQUIREMENT]
UID: FIX-DENY-REVOKED-TOKEN
STATUS: Active
TITLE: Deny revoked refresh/access token after sign-out
STATEMENT: >>>
FIXTURE / TEST BED (not a product feature). After sign-out (A02) or RFC 7009 revocation: the revoked refresh token → invalid_grant, and the revoked access token is rejected at the API → 401.
<<<
COMMENT: >>>
KIND: requirement
BASE_UID: FIX-DENY-REVOKED-TOKEN
VERSION_N: 0
rbac_op: auth:oauth:revoke
priority: 15
iteration: iter-r1
security.catalog_ref: AC-12
security.verification_note: Pairs ARCH-AUTH-REVOKE; ASD V-222578.
in_scope_of_contract: ReqALM product (build)
edge: → conforms_to to AC-12 (pin imprint=nist-800-53@rev5-dogfood-20261006)
edge: → conforms_to to V-222578 (pin imprint=asd-stig@v6r4)
<<<
RELATIONS:
- TYPE: Parent
  VALUE: SEC-FIX
- TYPE: Parent
  VALUE: ARCH-AUTH-REVOKE
  ROLE: Uses
- TYPE: Parent
  VALUE: A02
  ROLE: Uses
- TYPE: Parent
  VALUE: AC-12
  ROLE: ConformsTo
- TYPE: Parent
  VALUE: V-222578
  ROLE: ConformsTo
- TYPE: Child
  VALUE: CONTRACT-ctr-reqalm-product
  ROLE: InScopeOf

[REQUIREMENT]
UID: FIX-DENY-DCR-DISABLED
STATUS: Active
TITLE: Deny dynamic client registration when policy is off
STATEMENT: >>>
FIXTURE / TEST BED (not a product feature). With DCR policy off (default), AS metadata omits registration_endpoint and POST /register → 403 (or 404). No client row is created, and the attempt is audited.
<<<
COMMENT: >>>
KIND: requirement
BASE_UID: FIX-DENY-DCR-DISABLED
VERSION_N: 0
rbac_op: auth:client:register
priority: 20
iteration: iter-r1
security.catalog_ref: CM-7
security.verification_note: Pairs ARCH-AUTH-CLIENTREG.
in_scope_of_contract: ReqALM product (build)
edge: → conforms_to to CM-7 (pin imprint=nist-800-53@rev5-dogfood-20261006)
<<<
RELATIONS:
- TYPE: Parent
  VALUE: SEC-FIX
- TYPE: Parent
  VALUE: ARCH-AUTH-CLIENTREG
  ROLE: Uses
- TYPE: Parent
  VALUE: CM-7
  ROLE: ConformsTo
- TYPE: Child
  VALUE: CONTRACT-ctr-reqalm-product
  ROLE: InScopeOf

[REQUIREMENT]
UID: FIX-ALLOW-FEDERATED-SSO-VIA-AS
STATUS: Active
TITLE: Federated SSO yields internal-AS tokens for linked identity
STATEMENT: >>>
FIXTURE / TEST BED (not a product feature). dan signs in through the upstream IdP (external_sub oidc:dan-raby). The AS validates the assertion, maps it to identity dan, and issues internal-AS tokens (iss = ReqAML AS). The API accepts them and loads dan's reqaml grants; the upstream token never reaches the API.
<<<
COMMENT: >>>
KIND: requirement
BASE_UID: FIX-ALLOW-FEDERATED-SSO-VIA-AS
VERSION_N: 0
rbac_op: auth:signin
priority: 10
iteration: iter-r1
security.catalog_ref: IA-8
security.verification_note: Pairs ARCH-AUTH-FEDERATION / A01.
in_scope_of_contract: ReqALM product (build)
edge: → conforms_to to IA-8 (pin imprint=nist-800-53@rev5-dogfood-20261006)
<<<
RELATIONS:
- TYPE: Parent
  VALUE: SEC-FIX
- TYPE: Parent
  VALUE: ARCH-AUTH-FEDERATION
  ROLE: Uses
- TYPE: Parent
  VALUE: A01
  ROLE: Uses
- TYPE: Parent
  VALUE: IA-8
  ROLE: ConformsTo
- TYPE: Child
  VALUE: CONTRACT-ctr-reqalm-product
  ROLE: InScopeOf

[REQUIREMENT]
UID: FIX-DENY-LOCKOUT
STATUS: Active
TITLE: Lockout after N consecutive failed logins
STATEMENT: >>>
FIXTURE / TEST BED (not a product feature). Local dev account for taylor-tester: N consecutive wrong passwords inside the window (DoD preset 3 in 15 minutes) → account locked. The next login with the correct password is refused with the same generic error. Audit records each failure and the lockout. Unlock only via auth:account:unlock or the timer.
<<<
COMMENT: >>>
KIND: requirement
BASE_UID: FIX-DENY-LOCKOUT
VERSION_N: 0
rbac_op: auth:local:signin
priority: 10
iteration: iter-r1
security.catalog_ref: AC-7
security.verification_note: Pairs ARCH-CRED-LOCKOUT; ASD V-222432.
in_scope_of_contract: ReqALM product (build)
edge: → conforms_to to AC-7 (pin imprint=nist-800-53@rev5-dogfood-20261006)
edge: → conforms_to to V-222432 (pin imprint=asd-stig@v6r4)
<<<
RELATIONS:
- TYPE: Parent
  VALUE: SEC-FIX
- TYPE: Parent
  VALUE: ARCH-CRED-LOCKOUT
  ROLE: Uses
- TYPE: Parent
  VALUE: AC-7
  ROLE: ConformsTo
- TYPE: Parent
  VALUE: V-222432
  ROLE: ConformsTo
- TYPE: Child
  VALUE: CONTRACT-ctr-reqalm-product
  ROLE: InScopeOf

[REQUIREMENT]
UID: FIX-DENY-PRIV-NO-MFA
STATUS: Active
TITLE: Deny privileged action on a session without MFA
STATEMENT: >>>
FIXTURE / TEST BED (not a product feature). dan (Project admin) with a session lacking MFA evidence attempts project:grant:create → step-up required / 403. No grant is written, and the attempt is audited.
<<<
COMMENT: >>>
KIND: requirement
BASE_UID: FIX-DENY-PRIV-NO-MFA
VERSION_N: 0
rbac_op: project:grant:create
priority: 10
iteration: iter-r1
security.catalog_ref: IA-2.1
security.verification_note: Pairs ARCH-CRED-MFA; ASD V-222523.
in_scope_of_contract: ReqALM product (build)
edge: → conforms_to to IA-2.1 (pin imprint=nist-800-53@rev5-dogfood-20261006)
edge: → conforms_to to V-222523 (pin imprint=asd-stig@v6r4)
<<<
RELATIONS:
- TYPE: Parent
  VALUE: SEC-FIX
- TYPE: Parent
  VALUE: ARCH-CRED-MFA
  ROLE: Uses
- TYPE: Parent
  VALUE: A07
  ROLE: Uses
- TYPE: Parent
  VALUE: IA-2.1
  ROLE: ConformsTo
- TYPE: Parent
  VALUE: V-222523
  ROLE: ConformsTo
- TYPE: Child
  VALUE: CONTRACT-ctr-reqalm-product
  ROLE: InScopeOf

[REQUIREMENT]
UID: FIX-DENY-STEPUP-STALE-AUTH
STATUS: Active
TITLE: Deny approval/pin apply with stale authentication
STATEMENT: >>>
FIXTURE / TEST BED (not a product feature). pat-client-admin calls requirement:line:approve, or sam-security calls catalog:pin:apply, with auth_time older than max_age → 401 step-up challenge (insufficient_user_authentication). No ApprovalRecord or pin is written.
<<<
COMMENT: >>>
KIND: requirement
BASE_UID: FIX-DENY-STEPUP-STALE-AUTH
VERSION_N: 0
rbac_op: requirement:line:approve, catalog:pin:apply
priority: 10
iteration: iter-r1
security.catalog_ref: IA-11
security.verification_note: Pairs ARCH-CRED-REAUTH; ASD V-222520.
in_scope_of_contract: ReqALM product (build)
edge: → conforms_to to IA-11 (pin imprint=nist-800-53@rev5-dogfood-20261006)
edge: → conforms_to to V-222520 (pin imprint=asd-stig@v6r4)
<<<
RELATIONS:
- TYPE: Parent
  VALUE: SEC-FIX
- TYPE: Parent
  VALUE: ARCH-CRED-REAUTH
  ROLE: Uses
- TYPE: Parent
  VALUE: D12
  ROLE: Uses
- TYPE: Parent
  VALUE: IA-11
  ROLE: ConformsTo
- TYPE: Parent
  VALUE: V-222520
  ROLE: ConformsTo
- TYPE: Child
  VALUE: CONTRACT-ctr-reqalm-product
  ROLE: InScopeOf

[REQUIREMENT]
UID: FIX-DENY-SESSION-IDLE
STATUS: Active
TITLE: Deny after idle session timeout
STATEMENT: >>>
FIXTURE / TEST BED (not a product feature). Session idle past the configured timeout (DoD preset 15 minutes non-privileged, 10 minutes admin) → next API call 401. The session is destroyed and a session-timeout audit row is emitted.
<<<
COMMENT: >>>
KIND: requirement
BASE_UID: FIX-DENY-SESSION-IDLE
VERSION_N: 0
rbac_op: auth:session:manage
priority: 15
iteration: iter-r1
security.catalog_ref: AC-12
security.verification_note: Pairs ARCH-CRED-SESSION; ASD V-222389 / V-222390 / V-222445.
in_scope_of_contract: ReqALM product (build)
edge: → conforms_to to AC-12 (pin imprint=nist-800-53@rev5-dogfood-20261006)
edge: → conforms_to to V-222389 (pin imprint=asd-stig@v6r4)
<<<
RELATIONS:
- TYPE: Parent
  VALUE: SEC-FIX
- TYPE: Parent
  VALUE: ARCH-CRED-SESSION
  ROLE: Uses
- TYPE: Parent
  VALUE: AC-12
  ROLE: ConformsTo
- TYPE: Parent
  VALUE: V-222389
  ROLE: ConformsTo
- TYPE: Child
  VALUE: CONTRACT-ctr-reqalm-product
  ROLE: InScopeOf

[REQUIREMENT]
UID: FIX-ALLOW-CRED-HASH-ONLY
STATUS: Active
TITLE: Credential store holds only hashes / wrapped secrets
STATEMENT: >>>
FIXTURE / TEST BED (not a product feature). Inspection oracle on a seeded instance: no plaintext passwords, refresh tokens, authorization codes, or client secrets (hashes only, with algorithm and params recorded). Usable secrets exist only as DEK ciphertext, and DEKs exist only wrapped by the OpenBao Transit KEK.
<<<
COMMENT: >>>
KIND: requirement
BASE_UID: FIX-ALLOW-CRED-HASH-ONLY
VERSION_N: 0
priority: 15
iteration: iter-r1
security.catalog_ref: IA-5.1
security.verification_note: Pairs ARCH-CRED-HASH / ARCH-CRED-TOKENS / ARCH-KEY; ASD V-222542.
in_scope_of_contract: ReqALM product (build)
edge: → conforms_to to IA-5.1 (pin imprint=nist-800-53@rev5-dogfood-20261006)
edge: → conforms_to to V-222542 (pin imprint=asd-stig@v6r4)
<<<
RELATIONS:
- TYPE: Parent
  VALUE: SEC-FIX
- TYPE: Parent
  VALUE: ARCH-CRED-HASH
  ROLE: Uses
- TYPE: Parent
  VALUE: ARCH-CRED-TOKENS
  ROLE: Uses
- TYPE: Parent
  VALUE: ARCH-KEY
  ROLE: Uses
- TYPE: Parent
  VALUE: IA-5.1
  ROLE: ConformsTo
- TYPE: Parent
  VALUE: V-222542
  ROLE: ConformsTo
- TYPE: Child
  VALUE: CONTRACT-ctr-reqalm-product
  ROLE: InScopeOf

[REQUIREMENT]
UID: FIX-DENY-KEK-UNREACHABLE-PROD
STATUS: Active
TITLE: Prod start fails closed when KEK unreachable
STATEMENT: >>>
FIXTURE / TEST BED (not a product feature). Production config with OpenBao unreachable or sealed → app refuses to start or readiness stays not-ready, and health reports unhealthy. No plaintext or dev-key fallback. Audited and alerted.
<<<
COMMENT: >>>
KIND: requirement
BASE_UID: FIX-DENY-KEK-UNREACHABLE-PROD
VERSION_N: 0
priority: 10
iteration: iter-r1
security.catalog_ref: SC-24
security.verification_note: Pairs ARCH-KEY-FAILCLOSED.
in_scope_of_contract: ReqALM product (build)
edge: → conforms_to to SC-24 (pin imprint=nist-800-53@rev5-dogfood-20261006)
<<<
RELATIONS:
- TYPE: Parent
  VALUE: SEC-FIX
- TYPE: Parent
  VALUE: ARCH-KEY-FAILCLOSED
  ROLE: Uses
- TYPE: Parent
  VALUE: SC-24
  ROLE: ConformsTo
- TYPE: Child
  VALUE: CONTRACT-ctr-reqalm-product
  ROLE: InScopeOf

[REQUIREMENT]
UID: FIX-DENY-DEV-KEK-IN-PROD
STATUS: Active
TITLE: Deny dev OpenBao / dev keys in a prod build
STATEMENT: >>>
FIXTURE / TEST BED (not a product feature). Production build or config pointing at a dev OpenBao (dev-marked address, dev root token, or dev-marked Transit keys) → startup refused with an explicit error. No keys are unwrapped.
<<<
COMMENT: >>>
KIND: requirement
BASE_UID: FIX-DENY-DEV-KEK-IN-PROD
VERSION_N: 0
priority: 10
iteration: iter-r1
security.catalog_ref: CM-7
security.verification_note: Pairs ARCH-DEVENV-KEYS.
edge: ← satisfies from CAP-PROD-SELFCHECK
in_scope_of_contract: ReqALM product (build)
edge: → conforms_to to CM-7 (pin imprint=nist-800-53@rev5-dogfood-20261006)
<<<
RELATIONS:
- TYPE: Parent
  VALUE: SEC-FIX
- TYPE: Parent
  VALUE: ARCH-DEVENV-KEYS
  ROLE: Uses
- TYPE: Parent
  VALUE: CM-7
  ROLE: ConformsTo
- TYPE: Child
  VALUE: CONTRACT-ctr-reqalm-product
  ROLE: InScopeOf

[REQUIREMENT]
UID: FIX-JWKS-ROTATION-OVERLAP
STATUS: Active
TITLE: Rotated signing key verifies within overlap, rejected after
STATEMENT: >>>
FIXTURE / TEST BED (not a product feature). Transit signing key rotated v1 → v2. A token with kid=v1 still verifies inside the overlap window, and JWKS lists v1 and v2. After the window, v1 leaves JWKS and the same token → 401. New tokens carry kid=v2.
<<<
COMMENT: >>>
KIND: requirement
BASE_UID: FIX-JWKS-ROTATION-OVERLAP
VERSION_N: 0
rbac_op: key:signing:rotate
priority: 10
iteration: iter-r1
security.catalog_ref: SC-12.3
security.verification_note: Pairs ARCH-KEY-JWKS.
in_scope_of_contract: ReqALM product (build)
edge: → conforms_to to SC-12.3 (pin imprint=nist-800-53@rev5-dogfood-20261006)
<<<
RELATIONS:
- TYPE: Parent
  VALUE: SEC-FIX
- TYPE: Parent
  VALUE: ARCH-KEY-JWKS
  ROLE: Uses
- TYPE: Parent
  VALUE: SC-12.3
  ROLE: ConformsTo
- TYPE: Child
  VALUE: CONTRACT-ctr-reqalm-product
  ROLE: InScopeOf

[REQUIREMENT]
UID: FIX-DENY-KEYOP-NO-CUSTODIAN
STATUS: Active
TITLE: Deny key operation without Key custodian
STATEMENT: >>>
FIXTURE / TEST BED (not a product feature). pat-client-admin (Client admin, not Key custodian) attempts key:kek:rotate → 403 + audit deny. kim-key-custodian performing the same op → allowed after step-up.
<<<
COMMENT: >>>
KIND: requirement
BASE_UID: FIX-DENY-KEYOP-NO-CUSTODIAN
VERSION_N: 0
rbac_op: key:kek:rotate
priority: 10
iteration: iter-r1
security.catalog_ref: AC-5
security.verification_note: Pairs ARCH-KEY-CUSTODIAN.
in_scope_of_contract: ReqALM product (build)
edge: → conforms_to to AC-5 (pin imprint=nist-800-53@rev5-dogfood-20261006)
<<<
RELATIONS:
- TYPE: Parent
  VALUE: SEC-FIX
- TYPE: Parent
  VALUE: ARCH-KEY-CUSTODIAN
  ROLE: Uses
- TYPE: Parent
  VALUE: AC-5
  ROLE: ConformsTo
- TYPE: Child
  VALUE: CONTRACT-ctr-reqalm-product
  ROLE: InScopeOf

[REQUIREMENT]
UID: FIX-ALLOW-KEK-REWRAP-ONLINE
STATUS: Active
TITLE: KEK rotation re-wraps DEKs without downtime
STATEMENT: >>>
FIXTURE / TEST BED (not a product feature). KEK v1 → v2 while the app serves traffic. Every wrapped DEK is re-wrapped (Transit rewrap), and reads and writes succeed throughout. After verification the minimum decryption version is raised; v1 unwrap then fails and nothing depends on it. Each step is audited.
<<<
COMMENT: >>>
KIND: requirement
BASE_UID: FIX-ALLOW-KEK-REWRAP-ONLINE
VERSION_N: 0
rbac_op: key:kek:rotate, key:dek:rewrap
priority: 15
iteration: iter-r1
security.catalog_ref: SC-12
security.verification_note: Pairs ARCH-KEY-LIFECYCLE.
in_scope_of_contract: ReqALM product (build)
edge: → conforms_to to SC-12 (pin imprint=nist-800-53@rev5-dogfood-20261006)
<<<
RELATIONS:
- TYPE: Parent
  VALUE: SEC-FIX
- TYPE: Parent
  VALUE: ARCH-KEY-LIFECYCLE
  ROLE: Uses
- TYPE: Parent
  VALUE: SC-12
  ROLE: ConformsTo
- TYPE: Child
  VALUE: CONTRACT-ctr-reqalm-product
  ROLE: InScopeOf

[REQUIREMENT]
UID: FIX-ALLOW-DEVENV-MIN-CONTAINERS
STATUS: Active
TITLE: Default dev stack is at most 2 containers
STATEMENT: >>>
FIXTURE / TEST BED (not a product feature). From a fresh clone, the default compose up starts at most 2 containers (app + peripherals) and both report healthy. Hybrid mode starts only the peripherals container. The optional SoftHSM2 profile changes the app build target and does not add a peripheral container.
<<<
COMMENT: >>>
KIND: requirement
BASE_UID: FIX-ALLOW-DEVENV-MIN-CONTAINERS
VERSION_N: 0
priority: 15
iteration: iter-r0
security.catalog_ref: CM-2
security.verification_note: Pairs ARCH-DEPLOY-MINIMAL / ARCH-DEPLOY-PERIPHERALS.
edge: ← satisfies from CAP-DEVENV-COMPOSE
edge: ← satisfies from CAP-DEVENV-SMOKE
in_scope_of_contract: ReqALM product (build)
edge: → conforms_to to CM-2 (pin imprint=nist-800-53@rev5-dogfood-20261006)
<<<
RELATIONS:
- TYPE: Parent
  VALUE: SEC-FIX
- TYPE: Parent
  VALUE: ARCH-DEPLOY-MINIMAL
  ROLE: Uses
- TYPE: Parent
  VALUE: ARCH-DEPLOY-PERIPHERALS
  ROLE: Uses
- TYPE: Parent
  VALUE: ARCH-DEVENV-MODES.1
  ROLE: Uses
- TYPE: Parent
  VALUE: CM-2
  ROLE: ConformsTo
- TYPE: Child
  VALUE: CONTRACT-ctr-reqalm-product
  ROLE: InScopeOf

[REQUIREMENT]
UID: FIX-ALLOW-APP-ROLE-SPLIT
STATUS: Active
TITLE: App roles toggle by env; split without rebuild
STATEMENT: >>>
FIXTURE / TEST BED (not a product feature). The same app image started with REQAML_ROLES=sync runs only the sync worker (API/MCP/web endpoints absent, readiness reports sync only). With all roles enabled it serves API+AS, Web UI, and MCP and runs sync. No rebuild between runs.
<<<
COMMENT: >>>
KIND: requirement
BASE_UID: FIX-ALLOW-APP-ROLE-SPLIT
VERSION_N: 0
priority: 20
iteration: iter-r1
security.catalog_ref: CM-7
security.verification_note: Pairs ARCH-DEPLOY-MINIMAL; roles not enabled are not exposed.
edge: ← satisfies from CAP-DEVENV-DOCKERFILE-ROLES
in_scope_of_contract: ReqALM product (build)
edge: → conforms_to to CM-7 (pin imprint=nist-800-53@rev5-dogfood-20261006)
<<<
RELATIONS:
- TYPE: Parent
  VALUE: SEC-FIX
- TYPE: Parent
  VALUE: ARCH-DEPLOY-MINIMAL
  ROLE: Uses
- TYPE: Parent
  VALUE: CM-7
  ROLE: ConformsTo
- TYPE: Child
  VALUE: CONTRACT-ctr-reqalm-product
  ROLE: InScopeOf

[REQUIREMENT]
UID: FIX-DENY-LOCAL-LOGIN-PROFILE-OFF
STATUS: Active
TITLE: Local login denied/absent when profile disables local accounts
STATEMENT: >>>
FIXTURE / TEST BED (not a product feature). Production auth profile with local_accounts=disabled: the local login route returns 404 (absent) and the AS sign-in page offers only the configured upstream connector(s). Seeding or creating a local credential is refused. The inspection oracle finds no local credential rows, so A01 'no local password store' holds.
<<<
COMMENT: >>>
KIND: requirement
BASE_UID: FIX-DENY-LOCAL-LOGIN-PROFILE-OFF
VERSION_N: 0
rbac_op: auth:local:signin
priority: 10
iteration: iter-r1
security.catalog_ref: CM-7
security.verification_note: Pairs ARCH-AUTH-LOCAL.1 / ARCH-AUTH-PROFILE.
in_scope_of_contract: ReqALM product (build)
edge: → conforms_to to CM-7 (pin imprint=nist-800-53@rev5-dogfood-20261006)
<<<
RELATIONS:
- TYPE: Parent
  VALUE: SEC-FIX
- TYPE: Parent
  VALUE: ARCH-AUTH-LOCAL.1
  ROLE: Uses
- TYPE: Parent
  VALUE: ARCH-AUTH-PROFILE
  ROLE: Uses
- TYPE: Parent
  VALUE: A01
  ROLE: Uses
- TYPE: Parent
  VALUE: CM-7
  ROLE: ConformsTo
- TYPE: Child
  VALUE: CONTRACT-ctr-reqalm-product
  ROLE: InScopeOf

[REQUIREMENT]
UID: FIX-ALLOW-BREAKGLASS-LOCAL-ADMIN
STATUS: Active
TITLE: Break-glass local admin allowed only when enabled, with MFA, recovery-scoped
STATEMENT: >>>
FIXTURE / TEST BED (not a product feature). Profile local_accounts=breakglass_only with the upstream IdP connector down. A configured break-glass admin signs in with password + MFA and restores the connector (auth:connector:configure) → 200. An alert fires, audit rows are written, and the session uses the admin timeouts. Negative cases in the same bed: the break-glass account without MFA → denied; a requirement-content operation from that session → 403; an ordinary (non-break-glass) local login → denied.
<<<
COMMENT: >>>
KIND: requirement
BASE_UID: FIX-ALLOW-BREAKGLASS-LOCAL-ADMIN
VERSION_N: 0
rbac_op: auth:breakglass:signin, auth:connector:configure
priority: 15
iteration: iter-r1
security.catalog_ref: AC-2.2
security.verification_note: Pairs ARCH-AUTH-LOCAL-BREAKGLASS.
in_scope_of_contract: ReqALM product (build)
edge: → conforms_to to AC-2.2 (pin imprint=nist-800-53@rev5-dogfood-20261006)
edge: → conforms_to to IA-2.1 (pin imprint=nist-800-53@rev5-dogfood-20261006)
edge: → conforms_to to V-222410 (pin imprint=asd-stig@v6r4)
<<<
RELATIONS:
- TYPE: Parent
  VALUE: SEC-FIX
- TYPE: Parent
  VALUE: ARCH-AUTH-LOCAL-BREAKGLASS
  ROLE: Uses
- TYPE: Parent
  VALUE: ARCH-CRED-MFA
  ROLE: Uses
- TYPE: Parent
  VALUE: AC-2.2
  ROLE: ConformsTo
- TYPE: Parent
  VALUE: IA-2.1
  ROLE: ConformsTo
- TYPE: Parent
  VALUE: V-222410
  ROLE: ConformsTo
- TYPE: Child
  VALUE: CONTRACT-ctr-reqalm-product
  ROLE: InScopeOf

[REQUIREMENT]
UID: FIX-ALLOW-MCP-OAUTH-FEDERATED-ONLY
STATUS: Active
TITLE: MCP OAuth works with local accounts disabled (federated-only)
STATEMENT: >>>
FIXTURE / TEST BED (not a product feature). Profile identity_mode=federated, local_accounts=disabled. An MCP host (as alex-author) completes discovery and authorize at the internal AS, the AS brokers to the upstream connector, and returns an aud=MCP token. update_draft then succeeds, showing MCP OAuth does not depend on local accounts.
<<<
COMMENT: >>>
KIND: requirement
BASE_UID: FIX-ALLOW-MCP-OAUTH-FEDERATED-ONLY
VERSION_N: 0
rbac_op: auth:oauth:authorize, requirement:version:update_draft
priority: 10
iteration: iter-r1
security.catalog_ref: IA-2
security.verification_note: Pairs ARCH-AUTH-MCP-REQUIRED.
in_scope_of_contract: ReqALM product (build)
edge: → conforms_to to IA-2 (pin imprint=nist-800-53@rev5-dogfood-20261006)
edge: → conforms_to to IA-8 (pin imprint=nist-800-53@rev5-dogfood-20261006)
<<<
RELATIONS:
- TYPE: Parent
  VALUE: SEC-FIX
- TYPE: Parent
  VALUE: ARCH-AUTH-MCP-REQUIRED
  ROLE: Uses
- TYPE: Parent
  VALUE: ARCH-AUTH-FEDERATION
  ROLE: Uses
- TYPE: Parent
  VALUE: IA-2
  ROLE: ConformsTo
- TYPE: Parent
  VALUE: IA-8
  ROLE: ConformsTo
- TYPE: Child
  VALUE: CONTRACT-ctr-reqalm-product
  ROLE: InScopeOf

[REQUIREMENT]
UID: FIX-DENY-UPSTREAM-LOGOUT-PROPAGATED
STATUS: Active
TITLE: Upstream back-channel logout revokes ReqALM sessions and MCP tokens
STATEMENT: >>>
FIXTURE / TEST BED (not a product feature). dan has a UI session and an MCP refresh token, both from the upstream connector. The upstream IdP sends a back-channel logout for oidc:dan-raby, and the AS ends the sessions and revokes both token families. The next MCP refresh → invalid_grant and the UI call → 401. An audit row records the propagation.
<<<
COMMENT: >>>
KIND: requirement
BASE_UID: FIX-DENY-UPSTREAM-LOGOUT-PROPAGATED
VERSION_N: 0
rbac_op: auth:oauth:revoke
priority: 15
iteration: iter-r1
security.catalog_ref: AC-12
security.verification_note: Pairs ARCH-AUTH-UPSTREAM-REVOKE.
in_scope_of_contract: ReqALM product (build)
edge: → conforms_to to AC-12 (pin imprint=nist-800-53@rev5-dogfood-20261006)
edge: → conforms_to to V-222549 (pin imprint=asd-stig@v6r4)
<<<
RELATIONS:
- TYPE: Parent
  VALUE: SEC-FIX
- TYPE: Parent
  VALUE: ARCH-AUTH-UPSTREAM-REVOKE
  ROLE: Uses
- TYPE: Parent
  VALUE: AC-12
  ROLE: ConformsTo
- TYPE: Parent
  VALUE: V-222549
  ROLE: ConformsTo
- TYPE: Child
  VALUE: CONTRACT-ctr-reqalm-product
  ROLE: InScopeOf

[REQUIREMENT]
UID: FIX-DENY-CROSS-TENANT-CONNECTOR
STATUS: Active
TITLE: Client A's IdP connector cannot establish client B access
STATEMENT: >>>
FIXTURE / TEST BED (not a product feature). A valid assertion from raby-family's connector for a subject with no identity linked in other-family, used to sign in to other-family → no session for other-family. No identity is linked or created there, no grants are loaded, and the attempt is audited.
<<<
COMMENT: >>>
KIND: requirement
BASE_UID: FIX-DENY-CROSS-TENANT-CONNECTOR
VERSION_N: 0
rbac_op: auth:signin
priority: 15
iteration: iter-r1
security.catalog_ref: AC-3
security.verification_note: Pairs ARCH-AUTH-UPSTREAM-CONNECTOR / ARCH-CP-SCOPE.
in_scope_of_contract: ReqALM product (build)
edge: → conforms_to to AC-3 (pin imprint=nist-800-53@rev5-dogfood-20261006)
edge: → conforms_to to IA-8 (pin imprint=nist-800-53@rev5-dogfood-20261006)
<<<
RELATIONS:
- TYPE: Parent
  VALUE: SEC-FIX
- TYPE: Parent
  VALUE: ARCH-AUTH-UPSTREAM-CONNECTOR
  ROLE: Uses
- TYPE: Parent
  VALUE: ARCH-CP-SCOPE
  ROLE: Uses
- TYPE: Parent
  VALUE: AC-3
  ROLE: ConformsTo
- TYPE: Parent
  VALUE: IA-8
  ROLE: ConformsTo
- TYPE: Child
  VALUE: CONTRACT-ctr-reqalm-product
  ROLE: InScopeOf

[REQUIREMENT]
UID: FIX-ALLOW-AGENT-ATTRIBUTION
STATUS: Active
TITLE: MCP mutation audit names human subject + OAuth client
STATEMENT: >>>
FIXTURE / TEST BED (not a product feature). MCP update_draft by alex-author through MCP host client cursor-mcp → the audit row has identity_id=alex-author, oauth_client_id=cursor-mcp, jti, and source=mcp. There is no agent-only principal.
<<<
COMMENT: >>>
KIND: requirement
BASE_UID: FIX-ALLOW-AGENT-ATTRIBUTION
VERSION_N: 0
rbac_op: requirement:version:update_draft
priority: 15
iteration: iter-r1
security.catalog_ref: AU-3
security.verification_note: Pairs ARCH-AUTH-AGENT-ATTRIBUTION.
in_scope_of_contract: ReqALM product (build)
edge: → conforms_to to AU-3 (pin imprint=nist-800-53@rev5-dogfood-20261006)
edge: → conforms_to to AU-10 (pin imprint=nist-800-53@rev5-dogfood-20261006)
edge: → conforms_to to V-222438 (pin imprint=asd-stig@v6r4)
<<<
RELATIONS:
- TYPE: Parent
  VALUE: SEC-FIX
- TYPE: Parent
  VALUE: ARCH-AUTH-AGENT-ATTRIBUTION
  ROLE: Uses
- TYPE: Parent
  VALUE: MC02
  ROLE: Uses
- TYPE: Parent
  VALUE: AU-3
  ROLE: ConformsTo
- TYPE: Parent
  VALUE: AU-10
  ROLE: ConformsTo
- TYPE: Parent
  VALUE: V-222438
  ROLE: ConformsTo
- TYPE: Child
  VALUE: CONTRACT-ctr-reqalm-product
  ROLE: InScopeOf

[[/SECTION]]

[[SECTION]]
UID: SEC-WF
TITLE: Dynamic workflow system

[TEXT]
UID: SEC-WF-INTRO
STATEMENT: >>>
Dynamic workflow control plane for ReqAML: WorkflowProfile, SubjectKind registry, Gate, ActionHook, RoleBinding, thin Transition, and ApprovalRecord — composition over a mega-status enum (ARCH-WORKFLOW). See roles/workflow-system.md.
<<<

[REQUIREMENT]
UID: ARCH-WORKFLOW
STATUS: Active
TITLE: Composition: WorkflowProfile + Gate + ActionHook + RoleBinding (not mega-status)
STATEMENT: >>>
ReqAML workflow is composed of WorkflowProfile (per project, optional client default), SubjectKind registry, Gate, ActionHook, RoleBinding, thin Transition, and ApprovalRecord. Do NOT encode product control as one lifecycle megamachine. Lifecycle status (draft|active|obsolete|withdrawn) and grooming_state remain thin; gates/hooks evaluate at action time. Workflow is app logic + seed fixtures; StrictDoc stays interchange only.
<<<
COMMENT: >>>
KIND: requirement
BASE_UID: ARCH-WORKFLOW
VERSION_N: 0
rbac_op: workflow:architecture
priority: 10
iteration: iter-r0
security.catalog_ref: AU-2
security.verification_note: AU-2/3/12 workflow / approval audit.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: ARCH-SUBJECT-KIND
STATUS: Active
TITLE: SubjectKind registry (RequirementLine, CapabilityLine, edges, ChangeSet, Release)
STATEMENT: >>>
SubjectKinds register what can be a workflow subject: RequirementLine, CapabilityLine, RequirementVersion, EdgeSatisfies, EdgeConformsTo, ChangeSet, Release (extensible). Each declares stable id path, readable attributes for predicates, and allowed actions. Engine does not special-case every table in if/else forever.
<<<
COMMENT: >>>
KIND: requirement
BASE_UID: ARCH-SUBJECT-KIND
VERSION_N: 0
rbac_op: workflow:subject_kind
priority: 15
iteration: iter-r0
security.catalog_ref: AC-3
security.verification_note: AC-3 access enforcement; AU-2/3/12 where mutating.
edge: ← refines from ARCH-HIER-SECTION-GROUP
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: ARCH-REQ-VS-CAP
STATUS: Active
TITLE: Client sys-req vs CapabilityLine first-class; canonical need→solution path
STATEMENT: >>>
Client system requirements (RequirementLine: kind requirement|section|control) and contractor capabilities (CapabilityLine: kind=capability) share line/version storage but are distinct SubjectKinds with often different RoleBindings and gates. Canonical early path: draft client req → optional activate → line approve → create CapabilityLine with Satisfies → cap approve as solution → profile-gated planning (priority/grooming/…) → later ship with profile Gates. Satisfies is the primary coverage edge (not implements in v1 encode).
<<<
COMMENT: >>>
KIND: requirement
BASE_UID: ARCH-REQ-VS-CAP
VERSION_N: 0
rbac_op: workflow:req_vs_cap
priority: 10
iteration: iter-r0
security.catalog_ref: AC-3
security.verification_note: AC-3 access enforcement; AU-2/3/12 where mutating.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: ARCH-APPROVAL-LINE
STATUS: Active
TITLE: Approval grain = requirement line; pin approved_version_uid + statement_hash
STATEMENT: >>>
Approval grain is the requirement/capability LINE. ApprovalRecord stores status, by, at, notes, approved_version_uid, and approved_statement_hash. Tree UI batches many ApprovalRecords in one change set (Approve = line+direct children; Approve Tree = full descendants). Supersedes version-only wording; reconcile D08/D12/ARCH-APPROVAL to line grain + profile hooks. Version stakeholder_approval may dual-write as mirror.
<<<
COMMENT: >>>
KIND: requirement
BASE_UID: ARCH-APPROVAL-LINE
VERSION_N: 0
rbac_op: requirement:line:approval
priority: 10
iteration: iter-r0
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: ARCH-SUCCESSION-HASH
STATUS: Active
TITLE: statement_hash=body only; content .N clears; noop=content only
STATEMENT: >>>
statement_hash is the canonical hash of the STATEMENT BODY ONLY (trim whitespace; normalize newlines to \n; no status, pins, or security metadata in the hash — ARCH-MINT-KIND). Minting a successor .N with mint_kind=content ALWAYS clears the line ApprovalRecord to unapproved and sets planning_blocked until re-approve. Same statement_hash content mint is BLOCKED (gate-noop-successor-block / FIX-DENY-NOOP-CONTENT) — no-op content mint must not launder a clear. mint_kind=pin clears approval (locked migrate also needs gate_signoff then re-approve). mint_kind=status|security_meta do NOT clear approval (audit only). After clear, explicit approve is required again even if a later edit restores a prior hash (default).
<<<
COMMENT: >>>
KIND: requirement
BASE_UID: ARCH-SUCCESSION-HASH
VERSION_N: 0
rbac_op: requirement:version:mint
priority: 10
iteration: iter-r0
security.catalog_ref: AC-3
security.verification_note: AC-3 access enforcement; AU-2/3/12 where mutating.
edge: ← uses from FIX-DENY-NOOP-CONTENT
edge: ← uses from FIX-PLANNING-BLOCKED-AFTER-CONTENT-N
edge: ← uses from ARCH-MINT-KIND
edge: ← uses from ARCH-SUSPECT
edge: ← uses from ARCH-SUSPECT.1
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: ARCH-HOOK-EVAL
STATUS: Active
TITLE: ActionHook evaluator: RBAC → gates_before → mutate → effects_after → audit
STATEMENT: >>>
On each domain action: authorize RBAC (permission-tree) → load ActionHooks for the project's WorkflowProfile matching action_id → evaluate gates_before (skip optional gates disabled on profile) including RoleBinding slot checks → apply mutation → run effects_after (e.g. write_approval_record, clear_line_approval, audit) → ideally nest under change_set. RBAC = can attempt; gates = contextual allow.
<<<
COMMENT: >>>
KIND: requirement
BASE_UID: ARCH-HOOK-EVAL
VERSION_N: 0
rbac_op: workflow:hook_eval
priority: 15
iteration: iter-r0
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: ARCH-PLANNING-GATES
STATUS: Active
TITLE: Which planning actions need approval = profile-configurable
STATEMENT: >>>
Which planning mutations require line approval is profile-configurable via WorkflowProfile.planning_gate_actions and ActionHook gates_before — NOT permanently priority-only. Commercial default gates requirement:version:priority (D08). Profiles may also gate WI-ready (J01/K03), iteration assign (D09/K04), and release backlog membership (G03/G04). Engine reads the profile; dogfood ships both a narrow commercial and a broader DoD example profile.
<<<
COMMENT: >>>
KIND: requirement
BASE_UID: ARCH-PLANNING-GATES
VERSION_N: 0
rbac_op: workflow:planning_gates
priority: 15
iteration: iter-r1
security.catalog_ref: AC-3
security.verification_note: AC-3 access enforcement; AU-2/3/12 where mutating.
edge: ← satisfies from CAP-READ-PLANNING
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: ARCH-APPROVER-SLOTS
STATUS: Active
TITLE: Approver slots profile-configurable (many / one / contract-specific)
STATEMENT: >>>
Gate approver_slots are filled by RoleBinding (profile_id, gate_id, slot, roles[], optional identities[]). Supports many stakeholders, one overall approver, or contract-specific bindings — project/client configurable. Authors cannot redefine who fills a slot. D12/D13 mutate ApprovalRecord only if actor matches the bound slot. Commercial vs DoD differences are data, not hard-coded branches.
<<<
COMMENT: >>>
KIND: requirement
BASE_UID: ARCH-APPROVER-SLOTS
VERSION_N: 0
rbac_op: workflow:role_binding
priority: 15
iteration: iter-r0
security.catalog_ref: AC-3
security.verification_note: AC-3 access enforcement; AU-2/3/12 where mutating.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: ARCH-CAP-LINK
STATUS: Active
TITLE: Capabilities linked at creation via Satisfies (no orphan caps)
STATEMENT: >>>
CapabilityLine creation MUST include at least one Satisfies edge to a requirement version in the same mutation (gate-satisfies-at-create). No orphan capabilities. Additional Satisfies may be added later (E04). UI coaches link quality before capability approve.
<<<
COMMENT: >>>
KIND: requirement
BASE_UID: ARCH-CAP-LINK
VERSION_N: 0
rbac_op: capability:line:create
priority: 15
iteration: iter-r1
security.catalog_ref: AC-3
security.verification_note: AC-3 access enforcement; AU-2/3/12 where mutating.
edge: ← refines from ARCH-HIER-CAP-PARTOF
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: ARCH-CAP-APPROVE
STATUS: Active
TITLE: CapabilityLine approval enough for solution; Satisfies not separate approve subject
STATEMENT: >>>
CapabilityLine ApprovalRecord is sufficient to accept a capability as a solution. The Satisfies edge itself is NOT a separate approve subject by default (EdgeSatisfies remains a registered SubjectKind for hooks/structural gates). UI coaches link quality before approve. Profiles may later enable an optional Satisfies-approval gate without schema break.
<<<
COMMENT: >>>
KIND: requirement
BASE_UID: ARCH-CAP-APPROVE
VERSION_N: 0
rbac_op: capability:line:approve
priority: 15
iteration: iter-r1
security.catalog_ref: AC-3
security.verification_note: AC-3 access enforcement; AU-2/3/12 where mutating.
edge: ← refines from ARCH-CRED-REAUTH
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: ARCH-GATE-MODEL
STATUS: Active
TITLE: Cyber / verification / ship modeled as Gates under WorkflowProfile
STATEMENT: >>>
Cyber ship, verification→ship, line-approved→planning, noop-successor-block, and satisfies-at-create are Gates under WorkflowProfile — configurable composition, not one-off flags only. release.cyber_gate remains an example per-release switch that triggers gate-cyber-ship when the profile enables that gate (ARCH-CYBER-GATE). Same pattern for gate-verification-ship.
<<<
COMMENT: >>>
KIND: requirement
BASE_UID: ARCH-GATE-MODEL
VERSION_N: 0
rbac_op: workflow:gate_model
priority: 15
iteration: iter-r0
security.catalog_ref: CM-3
security.verification_note: CM-3 change control; gate evaluation.
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: ARCH-VERIFICATION-GATE
STATUS: Active
TITLE: verification_outcome first-class; configurable gate to ship
STATEMENT: >>>
verification_outcome is first-class. WorkflowProfile may enable gate-verification-ship so G05 ship requires delivers verification_outcome=pass (or profile predicate). When the gate is disabled, ship does not require pass. This replaces soft-only / permanently-dismissed verification policy with configurable Gates (ARCH-GATE-MODEL).
<<<
COMMENT: >>>
KIND: requirement
BASE_UID: ARCH-VERIFICATION-GATE
VERSION_N: 0
rbac_op: release:verification_gate
priority: 20
iteration: iter-r1
security.catalog_ref: AC-3
security.verification_note: AC-3 access enforcement; AU-2/3/12 where mutating.
in_scope_of_contract: ReqALM product (build)
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf

[REQUIREMENT]
UID: ARCH-MINT-KIND
STATUS: Active
TITLE: Mint kinds: content|status|pin|security_meta; noop gate = content only
STATEMENT: >>>
Successor mint carries mint_kind ∈ {content, status, pin, security_meta}. statement_hash is canonical STATEMENT BODY ONLY (trim + newline canonicalization — see ARCH-SUCCESSION-HASH). gate-noop-successor-block applies to content mints only: same statement_hash as head → deny (FIX-DENY-NOOP-CONTENT). status / pin / security_meta mints are exempt from the content no-op gate even when statement_hash is unchanged. Approval clear policy by mint_kind: content → clear ApprovalRecord; pin migrate → clear (+ DoD AO/Security gate_signoff on locked migrate then re-approve); status and security_meta → do NOT clear (audit only).
<<<
COMMENT: >>>
KIND: requirement
BASE_UID: ARCH-MINT-KIND
VERSION_N: 0
rbac_op: requirement:version:mint
priority: 15
iteration: iter-r1
security.catalog_ref: CM-3
security.verification_note: CM-3 change control; mint kinds / succession.
edge: ← uses from FIX-DENY-NOOP-CONTENT
edge: ← uses from FIX-ALLOW-PIN-MIGRATE-MINT
edge: ← refines from ARCH-WRITE-RESERVED-IDS
edge: ← refines from ARCH-ATTACH-PIN-VERSION
edge: ← refines from ARCH-ATTACH-VERSIONS
edge: ← refines from ARCH-ATTACH-PIN-VERSION.1
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-SUCCESSION-HASH
  ROLE: Uses
- TYPE: Child
  VALUE: CONTRACT-ctr-reqalm-product
  ROLE: InScopeOf
- TYPE: Child
  VALUE: RELEASE-rel-r1-core-alm
  ROLE: Delivers

[REQUIREMENT]
UID: ARCH-SUSPECT
STATUS: Draft
TITLE: trace_suspect on edges/junctions after content .N
STATEMENT: >>>
When a target line receives a content mint_kind=.N, inbound trace edges (satisfies/refines/uses) and contract in_scope_of / release delivers junctions that pin a prior version of that line are marked trace_suspect=true. Pin-only migrate (mint_kind=pin) updates the ConformsTo pin and does NOT suspect that pin. Generalizes catalog_drift to internal traces (P1-1). Detect bed: edge FIX-CONTRACT-DOC-NOCTX → FIX-SUCC-2HOP.1 (stale uses on superseded UID).
<<<
COMMENT: >>>
KIND: requirement
BASE_UID: ARCH-SUSPECT
VERSION_N: 0
rbac_op: trace:suspect
priority: 15
iteration: iter-r1
security.catalog_ref: AU-2
security.verification_note: AU-2/3/12 workflow / approval / suspect audit.
edge: ← uses from FIX-SUSPECT-ON-CONTENT-N
edge: ← uses from FIX-DENY-SHIP-WITH-OPEN-SUSPECT
edge: ← refines from ARCH-SUSPECT.1
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-SUCCESSION-HASH
  ROLE: Uses

[REQUIREMENT]
UID: ARCH-SUSPECT.1
STATUS: Active
TITLE: trace_suspect on edges/junctions after content .N
STATEMENT: >>>
When a target line receives a content mint_kind=.N, inbound trace edges (satisfies/refines/uses) and contract in_scope_of / release delivers junctions that pin a prior version of that line are marked trace_suspect=true. Pin-only migrate (mint_kind=pin) updates the ConformsTo pin and does NOT suspect that pin. Semantics for re-check vs incomplete and audit-sensitive rollups are defined in ARCH-TRACE-RECHECK; UI and APIs shall surface trace_suspect separately from incomplete. Detect bed: edge FIX-CONTRACT-DOC-NOCTX → FIX-SUCC-2HOP.1 (stale uses on superseded UID).
<<<
COMMENT: >>>
KIND: requirement
BASE_UID: ARCH-SUSPECT
VERSION_N: 1
rbac_op: trace:suspect
priority: 15
iteration: iter-r1
security.catalog_ref: AU-2
security.verification_note: Groomed 2026-10-09; .1 references ARCH-TRACE-RECHECK for re-check vs incomplete semantics.
edge: ← refines from ARCH-TRACE-RECHECK
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
edge: → uses to ARCH-TRACE-RECHECK (RELATIONS TYPE: Child; Parent would cycle)
<<<
RELATIONS:
- TYPE: Parent
  VALUE: SEC-WF
- TYPE: Parent
  VALUE: ARCH-SUSPECT
  ROLE: Refines
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-SUCCESSION-HASH
  ROLE: Uses
- TYPE: Child
  VALUE: ARCH-TRACE-RECHECK
  ROLE: Uses
- TYPE: Child
  VALUE: CONTRACT-ctr-reqalm-product
  ROLE: InScopeOf
- TYPE: Child
  VALUE: RELEASE-rel-r1-core-alm
  ROLE: Delivers

[REQUIREMENT]
UID: ARCH-SUSPECT-QUEUE
STATUS: Active
TITLE: Suspect review queue: carry / keep-pinned / drop
STATEMENT: >>>
Suspect review queue actions: carry-forward (retarget edge/junction to new tip), keep-pinned (acknowledge stale pin, clear suspect flag without retarget), drop (remove edge/junction). Every reaction is audited. Role defaults: Satisfies/refines/uses → Author; ConformsTo → Security; contract/release membership → Author + Release manager. Mirrors ARCH-CAT-REACT pattern for internal traces.
<<<
COMMENT: >>>
KIND: requirement
BASE_UID: ARCH-SUSPECT-QUEUE
VERSION_N: 0
rbac_op: trace:suspect:queue
priority: 15
iteration: iter-r1
security.catalog_ref: AU-2
security.verification_note: AU-2/3/12 workflow / approval / suspect audit.
edge: ← uses from FIX-ALLOW-SUSPECT-CARRY
edge: ← uses from FIX-ALLOW-SUSPECT-KEEP-PINNED
edge: ← uses from FIX-ALLOW-SUSPECT-DROP
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Child
  VALUE: CONTRACT-ctr-reqalm-product
  ROLE: InScopeOf
- TYPE: Child
  VALUE: RELEASE-rel-r1-core-alm
  ROLE: Delivers

[REQUIREMENT]
UID: ARCH-GATE-SIGNOFF
STATUS: Active
TITLE: gate_signoff record for cyber ship + locked migrate
STATEMENT: >>>
gate_signoff records store subject_kind, subject_id, gate_id, slot, identity_id, decision (approve|deny), at, note. Required for cyber ship (security_signoff + ao_approve on gate-cyber-ship) and for AO/Security sign-off on locked catalog migrate before re-approve. ApprovalRecord remains line-only; release/migrate sign-offs use gate_signoff (P1-4).
<<<
COMMENT: >>>
KIND: requirement
BASE_UID: ARCH-GATE-SIGNOFF
VERSION_N: 0
rbac_op: gate:signoff
priority: 15
iteration: iter-r1
security.catalog_ref: AC-3
security.verification_note: AC-3 access enforcement; AU-2/3/12 where mutating.
edge: ← uses from FIX-DENY-SHIP-UNSIGNED
edge: ← refines from ARCH-CRED-REAUTH
in_scope_of_contract: ReqALM product (build)
delivered_by_release: R1-core-ALM
edge: → conforms_to to AC-3 (pin imprint=nist-800-53@rev5-dogfood-20261006)
edge: → conforms_to to AU-2 (pin imprint=nist-800-53@rev5-dogfood-20261006)
edge: → conforms_to to AU-3 (pin imprint=nist-800-53@rev5-dogfood-20261006)
edge: → conforms_to to AU-12 (pin imprint=nist-800-53@rev5-dogfood-20261006)
<<<
RELATIONS:
- TYPE: Parent
  VALUE: SEC-WF
- TYPE: Parent
  VALUE: AC-3
  ROLE: ConformsTo
- TYPE: Parent
  VALUE: AU-2
  ROLE: ConformsTo
- TYPE: Parent
  VALUE: AU-3
  ROLE: ConformsTo
- TYPE: Parent
  VALUE: AU-12
  ROLE: ConformsTo
- TYPE: Parent
  VALUE: ARCH-CYBER-GATE
  ROLE: Uses
- TYPE: Child
  VALUE: CONTRACT-ctr-reqalm-product
  ROLE: InScopeOf
- TYPE: Child
  VALUE: RELEASE-rel-r1-core-alm
  ROLE: Delivers

[[/SECTION]]

[[SECTION]]
UID: SEC-DEVENV
TITLE: Developer environment & deployment topology

[TEXT]
UID: SEC-DEVENV-INTRO
STATEMENT: >>>
Developer environment and deployment topology for ReqAML. Docker Compose is the single supported local stand-up path and runs the fewest containers practical: one multi-role app container (API + internal OAuth AS, Web UI, MCP server, sync worker) and one peripherals container (Postgres + OpenBao), both built from one Dockerfile. Hybrid mode (peripherals only, app native with hot reload) and full-container mode are both supported. The clone-to-running path is short and documented, and migrations and the dogfood seed (with seeded dev accounts) load automatically or with one command. Sign-in goes through the internal AS, keys come from a dev OpenBao, and secrets stay out of source. Production builds ship no dev accounts, default credentials, or dev keys.
<<<

[REQUIREMENT]
UID: ARCH-DEVENV-COMPOSE
STATUS: Draft
TITLE: Compose is the single supported dev entry point (app + peripherals)
STATEMENT: >>>
Docker Compose is the single supported developer entry point for ReqAML. The repository includes the Compose file(s) and an env template. Compose services derive from the C4 L2 containers: Postgres (database), API (Node/TypeScript OpenAPI), Web UI (React), and Sync worker (DevOps work-item sync), plus a non-prod local identity stub for A01-aligned sign-in. Operators do not invent ad-hoc local wiring outside Compose for first-time stand-up.
<<<
COMMENT: >>>
KIND: requirement
BASE_UID: ARCH-DEVENV-COMPOSE
VERSION_N: 0
priority: 15
iteration: iter-r0
security.catalog_ref: CM-2
security.verification_note: CM-2 baseline: Compose + Dockerfile define the supported local/deploy baseline.
edge: ← refines from ARCH-DEVENV-MODES
edge: ← refines from ARCH-DEVENV-PARITY
edge: ← refines from ARCH-DEVENV-COMPOSE.1
edge: → conforms_to to CM-2 (pin imprint=nist-800-53@rev5-dogfood-20261006)
<<<
RELATIONS:
- TYPE: Parent
  VALUE: SEC-DEVENV
- TYPE: Parent
  VALUE: CM-2
  ROLE: ConformsTo

[REQUIREMENT]
UID: ARCH-DEVENV-COMPOSE.1
STATUS: Active
TITLE: Compose is the single supported dev entry point (app + peripherals)
STATEMENT: >>>
Docker Compose is the single supported developer entry point for ReqAML; the repository includes the Compose file(s) and an env template. The default stack is 2 containers, both from the repo's single Dockerfile: app (API with internal OAuth 2.1 AS, Web UI, MCP server, sync worker roles; ARCH-DEPLOY-MINIMAL) and peripherals (Postgres + OpenBao; ARCH-DEPLOY-PERIPHERALS). There is no third-party identity-stub container: local sign-in uses the internal AS with seeded dev accounts (ARCH-DEVENV-IDENTITY.1). An optional hsm-test profile builds the app with SoftHSM2 to exercise the PKCS#11 KeyProvider path without adding a peripheral container. Operators do not invent ad-hoc local wiring outside Compose for first-time stand-up.
<<<
COMMENT: >>>
KIND: requirement
BASE_UID: ARCH-DEVENV-COMPOSE
VERSION_N: 1
priority: 15
iteration: iter-r0
security.catalog_ref: CM-2
security.verification_note: CM-2 baseline: one Dockerfile + Compose define the supported local/deploy baseline.
edge: ← refines from ARCH-DEVENV-CLONE
edge: ← refines from ARCH-DEVENV-SEED
edge: ← refines from ARCH-DEVENV-HEALTH
edge: ← uses from ARCH-DEVENV-SECRETS
edge: ← refines from ARCH-DEVENV-MODES.1
edge: ← refines from ARCH-DEVENV-PARITY.1
edge: ← refines from ARCH-DEPLOY-MINIMAL
edge: ← refines from ARCH-DEPLOY-PERIPHERALS
edge: ← uses from ARCH-BUILD-FOUNDATION
edge: ← satisfies from CAP-DEVENV-COMPOSE
edge: ← satisfies from CAP-DEVENV-LF-ENDINGS
in_scope_of_contract: ReqALM product (build)
delivered_by_release: R1 platform follow-ups (deferred from foundation PR)
edge: → uses to ARCH-DEPLOY-MINIMAL (RELATIONS TYPE: Child; Parent would cycle)
edge: → uses to ARCH-DEPLOY-PERIPHERALS (RELATIONS TYPE: Child; Parent would cycle)
edge: → uses to ARCH-AUTH-AS (RELATIONS TYPE: Child; Parent would cycle)
edge: → conforms_to to CM-2 (pin imprint=nist-800-53@rev5-dogfood-20261006)
<<<
RELATIONS:
- TYPE: Parent
  VALUE: SEC-DEVENV
- TYPE: Parent
  VALUE: ARCH-DEVENV-COMPOSE
  ROLE: Refines
- TYPE: Parent
  VALUE: CM-2
  ROLE: ConformsTo
- TYPE: Child
  VALUE: ARCH-DEPLOY-MINIMAL
  ROLE: Uses
- TYPE: Child
  VALUE: ARCH-DEPLOY-PERIPHERALS
  ROLE: Uses
- TYPE: Child
  VALUE: ARCH-AUTH-AS
  ROLE: Uses
- TYPE: Child
  VALUE: CONTRACT-ctr-reqalm-product
  ROLE: InScopeOf
- TYPE: Child
  VALUE: RELEASE-rel-r1-platform-followups
  ROLE: Delivers

[[SECTION]]
UID: ARCH-DEVENV-COMPOSE-CHILDREN
TITLE: Children of ARCH-DEVENV-COMPOSE

[REQUIREMENT]
UID: ARCH-DEVENV-MODES
STATUS: Draft
TITLE: Hybrid (peripherals only + native app) and full-container run modes
STATEMENT: >>>
ReqAML supports two Compose-backed run modes: (1) hybrid — Compose provides dependencies (at least Postgres and the local identity stub); the API and/or Web UI run as native Node processes with hot reload against those deps; (2) full-container — API, Web UI, Sync worker, and dependencies all run as Compose services from built images. Both modes share the same Compose project and env contract so developers can switch without re-wiring.
<<<
COMMENT: >>>
KIND: requirement
BASE_UID: ARCH-DEVENV-MODES
VERSION_N: 0
priority: 15
iteration: iter-r0
security.catalog_ref: CM-2
security.verification_note: CM-2 baseline: Compose + Dockerfile define the supported local/deploy baseline.
edge: ← uses from ARCH-DEVENV-PARITY
edge: ← refines from ARCH-DEVENV-MODES.1
edge: → conforms_to to CM-2 (pin imprint=nist-800-53@rev5-dogfood-20261006)
<<<
RELATIONS:
- TYPE: Parent
  VALUE: ARCH-DEVENV-COMPOSE.1
- TYPE: Parent
  VALUE: ARCH-DEVENV-COMPOSE
  ROLE: Refines
- TYPE: Parent
  VALUE: CM-2
  ROLE: ConformsTo

[REQUIREMENT]
UID: ARCH-DEVENV-MODES.1
STATUS: Active
TITLE: Hybrid (peripherals only + native app) and full-container run modes
STATEMENT: >>>
ReqAML supports two Compose-backed run modes. (1) Hybrid: Compose runs only the peripherals container (Postgres + OpenBao), and the app runs natively as one Node process with all roles enabled and hot reload. (2) Full-container: Compose runs the app container (same image as deployment) plus the peripherals container. Both modes share the same Compose project, env contract, and OpenBao dev KeyProvider, so developers can switch without re-wiring.
<<<
COMMENT: >>>
KIND: requirement
BASE_UID: ARCH-DEVENV-MODES
VERSION_N: 1
priority: 15
iteration: iter-r0
security.catalog_ref: CM-2
security.verification_note: CM-2 baseline: one Dockerfile + Compose define the supported local/deploy baseline.
edge: ← uses from ARCH-DEVENV-PARITY.1
edge: ← uses from FIX-ALLOW-DEVENV-MIN-CONTAINERS
edge: ← satisfies from CAP-DEVENV-COMPOSE
in_scope_of_contract: ReqALM product (build)
delivered_by_release: PR #12 — devenv foundation
edge: → conforms_to to CM-2 (pin imprint=nist-800-53@rev5-dogfood-20261006)
<<<
RELATIONS:
- TYPE: Parent
  VALUE: ARCH-DEVENV-COMPOSE.1
- TYPE: Parent
  VALUE: ARCH-DEVENV-COMPOSE.1
  ROLE: Refines
- TYPE: Parent
  VALUE: ARCH-DEVENV-MODES
  ROLE: Refines
- TYPE: Parent
  VALUE: ARCH-DEVENV-KEYS
  ROLE: Uses
- TYPE: Parent
  VALUE: ARCH-DEPLOY-PERIPHERALS
  ROLE: Uses
- TYPE: Parent
  VALUE: CM-2
  ROLE: ConformsTo
- TYPE: Child
  VALUE: CONTRACT-ctr-reqalm-product
  ROLE: InScopeOf
- TYPE: Child
  VALUE: RELEASE-rel-pr12-devenv-foundation
  ROLE: Delivers

[REQUIREMENT]
UID: ARCH-DEVENV-CLONE
STATUS: Active
TITLE: Clone-to-running documented short path
STATEMENT: >>>
A new developer clones the repo and reaches a working instance via a documented short sequence (for example: copy env template → compose up → open the published URL) without manual database schema setup. Target: a healthy UI/API against a migrated database with dogfood fixtures available for local exercise. Documentation lives in-repo beside the Compose files.
<<<
COMMENT: >>>
KIND: requirement
BASE_UID: ARCH-DEVENV-CLONE
VERSION_N: 0
priority: 10
iteration: iter-r0
security.catalog_ref: CM-2
security.verification_note: CM-2 baseline: Compose + Dockerfile define the supported local/deploy baseline.
edge: ← uses from ARCH-DEVENV-SEED
edge: ← uses from FIX-ALLOW-DEVENV-SMOKE
edge: ← satisfies from CAP-DEVENV-MONOREPO
edge: ← satisfies from CAP-DEVENV-COMPOSE
edge: ← satisfies from CAP-API-DOCS-SEED-SUMMARY
edge: ← satisfies from CAP-DEVENV-LF-ENDINGS
in_scope_of_contract: ReqALM product (build)
delivered_by_release: PR #12 — devenv foundation
edge: → conforms_to to CM-2 (pin imprint=nist-800-53@rev5-dogfood-20261006)
<<<
RELATIONS:
- TYPE: Parent
  VALUE: ARCH-DEVENV-COMPOSE.1
- TYPE: Parent
  VALUE: ARCH-DEVENV-COMPOSE.1
  ROLE: Refines
- TYPE: Parent
  VALUE: ARCH-DEVENV-HEALTH
  ROLE: Uses
- TYPE: Parent
  VALUE: ARCH-DEVENV-SEED
  ROLE: Uses
- TYPE: Parent
  VALUE: ARCH-DEVENV-IDENTITY.1
  ROLE: Uses
- TYPE: Parent
  VALUE: CM-2
  ROLE: ConformsTo
- TYPE: Child
  VALUE: CONTRACT-ctr-reqalm-product
  ROLE: InScopeOf
- TYPE: Child
  VALUE: RELEASE-rel-pr12-devenv-foundation
  ROLE: Delivers

[REQUIREMENT]
UID: ARCH-DEVENV-SEED
STATUS: Active
TITLE: Migrations and dogfood seed on first start (idempotent)
STATEMENT: >>>
On first start (or via one documented command), database migrations and the dogfood seed load run so a fresh instance can act as fixture data and a test oracle. Re-running migrations and seed load is idempotent: repeat application does not duplicate rows or fail on already-applied schema. Seed load must not be required as a production deployment step.
<<<
COMMENT: >>>
KIND: requirement
BASE_UID: ARCH-DEVENV-SEED
VERSION_N: 0
priority: 15
iteration: iter-r0
security.catalog_ref: CM-6
security.verification_note: CM-6 configuration settings via Compose + .env; no secrets in source.
edge: ← uses from ARCH-DEVENV-CLONE
edge: ← uses from FIX-ALLOW-DEVENV-SMOKE
edge: ← uses from FIX-ALLOW-DEVENV-SEED-IDEMPOTENT
edge: ← uses from ARCH-DEVENV-IDENTITY.1
edge: ← satisfies from CAP-DEVENV-MIGRATE-SEED
edge: ← satisfies from CAP-DEVENV-SEED-RESET
edge: ← refines from ARCH-SEC-SEED-INTEGRITY
edge: ← refines from ARCH-SEC-LOADER-EDGE-SYNC
in_scope_of_contract: ReqALM product (build)
delivered_by_release: PR #12 — devenv foundation
edge: → uses to ARCH-DEVENV-CLONE (RELATIONS TYPE: Child; Parent would cycle)
edge: → conforms_to to CM-6 (pin imprint=nist-800-53@rev5-dogfood-20261006)
<<<
RELATIONS:
- TYPE: Parent
  VALUE: ARCH-DEVENV-COMPOSE.1
- TYPE: Parent
  VALUE: ARCH-DEVENV-COMPOSE.1
  ROLE: Refines
- TYPE: Parent
  VALUE: CM-6
  ROLE: ConformsTo
- TYPE: Child
  VALUE: ARCH-DEVENV-CLONE
  ROLE: Uses
- TYPE: Child
  VALUE: CONTRACT-ctr-reqalm-product
  ROLE: InScopeOf
- TYPE: Child
  VALUE: RELEASE-rel-pr12-devenv-foundation
  ROLE: Delivers

[REQUIREMENT]
UID: ARCH-DEVENV-PARITY
STATUS: Draft
TITLE: Single Dockerfile; app target matches deployment image
STATEMENT: >>>
The container image used for full-container development is built from the same Dockerfile used for deployment (multi-stage builds are allowed). Dev/prod differences are configuration and Compose overrides (ports, env, volume mounts, hot-reload sidecars), not a divergent Dockerfile tree, so local container runs exercise the deployable image contract.
<<<
COMMENT: >>>
KIND: requirement
BASE_UID: ARCH-DEVENV-PARITY
VERSION_N: 0
priority: 20
iteration: iter-r0
security.catalog_ref: CM-2
security.verification_note: CM-2 baseline: Compose + Dockerfile define the supported local/deploy baseline.
edge: ← refines from ARCH-DEVENV-PARITY.1
edge: → conforms_to to CM-2 (pin imprint=nist-800-53@rev5-dogfood-20261006)
<<<
RELATIONS:
- TYPE: Parent
  VALUE: ARCH-DEVENV-COMPOSE.1
- TYPE: Parent
  VALUE: ARCH-DEVENV-COMPOSE
  ROLE: Refines
- TYPE: Parent
  VALUE: ARCH-DEVENV-MODES
  ROLE: Uses
- TYPE: Parent
  VALUE: CM-2
  ROLE: ConformsTo

[REQUIREMENT]
UID: ARCH-DEVENV-PARITY.1
STATUS: Active
TITLE: Single Dockerfile; app target matches deployment image
STATEMENT: >>>
There is one Dockerfile with multi-stage targets. The app target that full-container dev runs is the same target used for deployment. Dev/prod differences are configuration, enabled roles, and Compose overrides only (ports, env, mounts), never a divergent Dockerfile tree. The peripherals target is for dev/test only; production runs Postgres and OpenBao as separate units (ARCH-DEPLOY-PERIPHERALS). The hsm-test target (SoftHSM2) is never deployed.
<<<
COMMENT: >>>
KIND: requirement
BASE_UID: ARCH-DEVENV-PARITY
VERSION_N: 1
priority: 20
iteration: iter-r0
security.catalog_ref: CM-2
security.verification_note: CM-2 baseline: one Dockerfile + Compose define the supported local/deploy baseline.
edge: ← satisfies from CAP-DEVENV-DOCKERFILE-ROLES
in_scope_of_contract: ReqALM product (build)
delivered_by_release: PR #12 — devenv foundation
edge: → conforms_to to CM-2 (pin imprint=nist-800-53@rev5-dogfood-20261006)
<<<
RELATIONS:
- TYPE: Parent
  VALUE: ARCH-DEVENV-COMPOSE.1
- TYPE: Parent
  VALUE: ARCH-DEVENV-COMPOSE.1
  ROLE: Refines
- TYPE: Parent
  VALUE: ARCH-DEVENV-MODES.1
  ROLE: Uses
- TYPE: Parent
  VALUE: ARCH-DEVENV-PARITY
  ROLE: Refines
- TYPE: Parent
  VALUE: ARCH-DEPLOY-MINIMAL
  ROLE: Uses
- TYPE: Parent
  VALUE: ARCH-DEPLOY-PERIPHERALS
  ROLE: Uses
- TYPE: Parent
  VALUE: CM-2
  ROLE: ConformsTo
- TYPE: Child
  VALUE: CONTRACT-ctr-reqalm-product
  ROLE: InScopeOf
- TYPE: Child
  VALUE: RELEASE-rel-pr12-devenv-foundation
  ROLE: Delivers

[REQUIREMENT]
UID: ARCH-DEVENV-HEALTH
STATUS: Active
TITLE: Compose service health checks and readiness
STATEMENT: >>>
Compose services define health checks and readiness so `compose up` (and dependents) report healthy only when dependencies are ready. API readiness aligns with M04 (health/version without leaking client data). Unhealthy deps must block or clearly fail dependent app start rather than silently serving a broken instance.
<<<
COMMENT: >>>
KIND: requirement
BASE_UID: ARCH-DEVENV-HEALTH
VERSION_N: 0
rbac_op: ops:health
priority: 15
iteration: iter-r0
security.catalog_ref: CM-6
security.verification_note: CM-6 configuration settings via Compose + .env; no secrets in source.
edge: ← uses from ARCH-DEVENV-CLONE
edge: ← uses from FIX-ALLOW-DEVENV-SMOKE
edge: ← uses from ARCH-KEY-FAILCLOSED
edge: ← satisfies from CAP-READY-PROBES
edge: ← satisfies from CAP-DEVENV-STARTUP-BACKOFF
in_scope_of_contract: ReqALM product (build)
delivered_by_release: PR #12 — devenv foundation
edge: → conforms_to to CM-6 (pin imprint=nist-800-53@rev5-dogfood-20261006)
<<<
RELATIONS:
- TYPE: Parent
  VALUE: ARCH-DEVENV-COMPOSE.1
- TYPE: Parent
  VALUE: ARCH-DEVENV-COMPOSE.1
  ROLE: Refines
- TYPE: Parent
  VALUE: M04
  ROLE: Uses
- TYPE: Parent
  VALUE: CM-6
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-DEVENV-LF-ENDINGS
STATUS: Active
TITLE: Git LF line endings for Compose entrypoints
STATEMENT: >>>
Repository line endings are enforced for the Compose dev stack: a root .gitattributes keeps shell entrypoints and Docker/Compose context files as LF in Git so Linux containers never see a bash\r shebang when Windows Git checks out with core.autocrlf=true. Documented recovery re-normalizes an existing Windows working tree after pulling the fix.
<<<
COMMENT: >>>
KIND: capability
BASE_UID: CAP-DEVENV-LF-ENDINGS
VERSION_N: 0
priority: 10
iteration: iter-r1
security.catalog_ref: CM-2
security.verification_note: Shipped with Git LF line endings PR #35 (merge 5cac83400c5c0fe9b2b4c54db408f5850821c395); Windows core.autocrlf=true checkout test confirms shell entrypoints remain LF.
in_scope_of_contract: ReqALM product (build)
delivered_by_release: R1 — Git LF line endings (Compose entrypoints)
edge: → conforms_to to CM-2 (pin imprint=nist-800-53@rev5-dogfood-20261006)
<<<
RELATIONS:
- TYPE: Parent
  VALUE: ARCH-DEVENV-COMPOSE.1
- TYPE: Parent
  VALUE: ARCH-DEVENV-CLONE
  ROLE: Satisfies
- TYPE: Parent
  VALUE: ARCH-DEVENV-COMPOSE.1
  ROLE: Satisfies
- TYPE: Parent
  VALUE: ARCH-DEPLOY-MINIMAL
  ROLE: Satisfies
- TYPE: Parent
  VALUE: ARCH-DEPLOY-PERIPHERALS
  ROLE: Satisfies
- TYPE: Parent
  VALUE: CM-2
  ROLE: ConformsTo
- TYPE: Child
  VALUE: CONTRACT-ctr-reqalm-product
  ROLE: InScopeOf
- TYPE: Child
  VALUE: RELEASE-rel-r1-lf-endings
  ROLE: Delivers

[[/SECTION]]

[REQUIREMENT]
UID: ARCH-DEVENV-IDENTITY
STATUS: Draft
TITLE: Seeded dev accounts on the internal AS; none in production
STATEMENT: >>>
Local development provides a way to sign in without the enterprise IdP (a local OIDC stub or equivalent dev-login path) so A01 session establishment, grants, and Scoped View can be exercised offline. The local identity path is clearly disabled or omitted in production builds and configurations (CM-7 / V-222518). Production continues to require enterprise SSO only (A01 / REQAML-SEC-SSO); no local password store is introduced for production. Which stub implementation is used is an open product choice until Dan locks it.
<<<
COMMENT: >>>
KIND: requirement
BASE_UID: ARCH-DEVENV-IDENTITY
VERSION_N: 0
rbac_op: auth:signin
priority: 10
iteration: iter-r0
security.catalog_ref: CM-7
security.verification_note: CM-7 least functionality: local identity stub is non-essential and disabled in production.
edge: ← uses from FIX-DENY-DEVENV-PROD-LOGIN
edge: ← refines from ARCH-DEVENV-IDENTITY.1
edge: → conforms_to to CM-7 (pin imprint=nist-800-53@rev5-dogfood-20261006)
edge: → conforms_to to IA-2 (pin imprint=nist-800-53@rev5-dogfood-20261006)
edge: → conforms_to to V-222518 (pin imprint=asd-stig@v6r4)
<<<
RELATIONS:
- TYPE: Parent
  VALUE: SEC-DEVENV
- TYPE: Parent
  VALUE: A01
  ROLE: Refines
- TYPE: Parent
  VALUE: CAP-SSO
  ROLE: Uses
- TYPE: Parent
  VALUE: CM-7
  ROLE: ConformsTo
- TYPE: Parent
  VALUE: IA-2
  ROLE: ConformsTo
- TYPE: Parent
  VALUE: V-222518
  ROLE: ConformsTo

[REQUIREMENT]
UID: ARCH-DEVENV-IDENTITY.1
STATUS: Active
TITLE: Seeded dev accounts on the internal AS; none in production
STATEMENT: >>>
Local development signs in through ReqAML's internal OAuth AS (ARCH-AUTH-AS) with seeded dev local accounts mapped to the dogfood seed identities, so A01/A02 sessions, grants, Scoped View, and MCP authorization can be exercised offline. Dev account credentials are never committed: they come from the local env file or are generated at first seed and shown locally. Seeded dev accounts and the dev seed loader are dev-only. Production builds and configs ship no seeded dev accounts and no default credentials, and the seed loader refuses to create accounts in production mode. In production, enterprise SSO federates through the same AS (ARCH-AUTH-FEDERATION). This replaces the earlier third-party local OIDC stub idea.
<<<
COMMENT: >>>
KIND: requirement
BASE_UID: ARCH-DEVENV-IDENTITY
VERSION_N: 1
rbac_op: auth:signin
priority: 10
iteration: iter-r0
security.catalog_ref: CM-7
security.verification_note: CM-7 least functionality; IA-5 default authenticators; ASD V-222662 / V-222661 / V-222642.
edge: ← uses from ARCH-DEVENV-CLONE
edge: ← uses from FIX-DENY-DEVENV-PROD-LOGIN.1
edge: ← uses from ARCH-AUTH-PROFILE
edge: ← satisfies from CAP-PROD-SELFCHECK
edge: ← satisfies from CAP-DEVENV-INIT
in_scope_of_contract: ReqALM product (build)
delivered_by_release: R1 — foundation shell + internal auth
edge: → uses to ARCH-AUTH-LOCAL.1 (RELATIONS TYPE: Child; Parent would cycle)
edge: → conforms_to to CM-7 (pin imprint=nist-800-53@rev5-dogfood-20261006)
edge: → conforms_to to IA-2 (pin imprint=nist-800-53@rev5-dogfood-20261006)
edge: → conforms_to to IA-5 (pin imprint=nist-800-53@rev5-dogfood-20261006)
edge: → conforms_to to V-222662 (pin imprint=asd-stig@v6r4)
edge: → conforms_to to V-222661 (pin imprint=asd-stig@v6r4)
edge: → conforms_to to V-222642 (pin imprint=asd-stig@v6r4)
<<<
RELATIONS:
- TYPE: Parent
  VALUE: SEC-DEVENV
- TYPE: Parent
  VALUE: A01
  ROLE: Refines
- TYPE: Parent
  VALUE: CAP-SSO
  ROLE: Uses
- TYPE: Parent
  VALUE: ARCH-DEVENV-IDENTITY
  ROLE: Refines
- TYPE: Parent
  VALUE: ARCH-AUTH-AS
  ROLE: Uses
- TYPE: Parent
  VALUE: ARCH-DEVENV-SEED
  ROLE: Uses
- TYPE: Parent
  VALUE: CM-7
  ROLE: ConformsTo
- TYPE: Parent
  VALUE: IA-2
  ROLE: ConformsTo
- TYPE: Parent
  VALUE: IA-5
  ROLE: ConformsTo
- TYPE: Parent
  VALUE: V-222662
  ROLE: ConformsTo
- TYPE: Parent
  VALUE: V-222661
  ROLE: ConformsTo
- TYPE: Parent
  VALUE: V-222642
  ROLE: ConformsTo
- TYPE: Child
  VALUE: ARCH-AUTH-LOCAL.1
  ROLE: Uses
- TYPE: Child
  VALUE: CONTRACT-ctr-reqalm-product
  ROLE: InScopeOf
- TYPE: Child
  VALUE: RELEASE-rel-r1-foundation-shell-auth
  ROLE: Delivers

[REQUIREMENT]
UID: ARCH-DEVENV-SECRETS
STATUS: Active
TITLE: No secrets committed; .env.example; prod config separate
STATEMENT: >>>
No secrets (IdP client secrets, DB passwords, signing keys, API tokens) are committed to source control. The repo ships `.env.example` (or equivalent) with safe non-secret development defaults only. Production configuration is supplied separately (platform secrets / env injection) and is not the same file tree as the committed example. Aligns to CM-6 configuration settings and IA-5 authenticator protection.
<<<
COMMENT: >>>
KIND: requirement
BASE_UID: ARCH-DEVENV-SECRETS
VERSION_N: 0
priority: 10
iteration: iter-r0
security.catalog_ref: IA-5
security.verification_note: IA-5 authenticator protection: no secrets/authenticators committed to source.
edge: ← refines from ARCH-KEY
edge: ← uses from ARCH-KEY-PROVIDER
edge: ← satisfies from CAP-DEVENV-COMPOSE
edge: ← satisfies from CAP-DEVENV-INIT
in_scope_of_contract: ReqALM product (build)
delivered_by_release: PR #12 — devenv foundation
edge: → conforms_to to CM-6 (pin imprint=nist-800-53@rev5-dogfood-20261006)
edge: → conforms_to to IA-5 (pin imprint=nist-800-53@rev5-dogfood-20261006)
<<<
RELATIONS:
- TYPE: Parent
  VALUE: SEC-DEVENV
- TYPE: Parent
  VALUE: ARCH-DEVENV-COMPOSE.1
  ROLE: Uses
- TYPE: Parent
  VALUE: CM-6
  ROLE: ConformsTo
- TYPE: Parent
  VALUE: IA-5
  ROLE: ConformsTo
- TYPE: Child
  VALUE: CONTRACT-ctr-reqalm-product
  ROLE: InScopeOf
- TYPE: Child
  VALUE: RELEASE-rel-pr12-devenv-foundation
  ROLE: Delivers

[REQUIREMENT]
UID: ARCH-DEVENV-KEYS
STATUS: Active
TITLE: Dev KeyProvider: OpenBao dev instance; dev keys never valid in prod
STATEMENT: >>>
Development uses OpenBao (Transit engine) in the peripherals container as the default KeyProvider, which is the same provider type as the production default. On first start it initializes with dev-only seal/unseal material and a root token generated locally into git-ignored files (never committed). Storage persists so wrapped DEKs survive restarts, and Transit keys are dev-marked. Dev OpenBao instances and dev keys are never valid in production: production runs its own OpenBao with its own seal, and the app refuses dev-marked addresses or keys in prod mode. SoftHSM2 is optional and exists only to exercise the PKCS#11 provider path (app hsm-test build target).
<<<
COMMENT: >>>
KIND: requirement
BASE_UID: ARCH-DEVENV-KEYS
VERSION_N: 0
priority: 10
iteration: iter-r1
security.catalog_ref: CM-7
security.verification_note: CM-7 least functionality; dev key path non-essential in prod. ASD V-222642.
edge: ← uses from ARCH-DEVENV-MODES.1
edge: ← uses from FIX-DENY-DEV-KEK-IN-PROD
edge: ← satisfies from CAP-DEVENV-PERIPHERALS
edge: ← satisfies from CAP-PROD-SELFCHECK
edge: ← satisfies from CAP-DEVENV-OPENBAO-BOOTSTRAP
in_scope_of_contract: ReqALM product (build)
delivered_by_release: PR #12 — devenv foundation
edge: → conforms_to to CM-7 (pin imprint=nist-800-53@rev5-dogfood-20261006)
edge: → conforms_to to V-222642 (pin imprint=asd-stig@v6r4)
<<<
RELATIONS:
- TYPE: Parent
  VALUE: SEC-DEVENV
- TYPE: Parent
  VALUE: ARCH-KEY-PROVIDER
  ROLE: Refines
- TYPE: Parent
  VALUE: ARCH-DEPLOY-PERIPHERALS
  ROLE: Uses
- TYPE: Parent
  VALUE: CM-7
  ROLE: ConformsTo
- TYPE: Parent
  VALUE: V-222642
  ROLE: ConformsTo
- TYPE: Child
  VALUE: CONTRACT-ctr-reqalm-product
  ROLE: InScopeOf
- TYPE: Child
  VALUE: RELEASE-rel-pr12-devenv-foundation
  ROLE: Delivers

[REQUIREMENT]
UID: ARCH-DEPLOY-MINIMAL
STATUS: Active
TITLE: One Dockerfile; one multi-role app container (API+AS, Web UI, MCP, sync)
STATEMENT: >>>
One Dockerfile with multi-stage targets (app, peripherals, optional hsm-test) builds every ReqAML image. A single app container runs the API (including the internal OAuth AS), Web UI (static assets served by the API role), MCP server (Streamable HTTP), and sync worker together, as one Node process or under a lightweight supervisor. Roles are toggled by env/config (for example REQAML_ROLES=api,web,mcp,sync), so any role can later run as its own container from the same image without a rebuild, and health/readiness is reported per enabled role. Rationale (Dan, 2026-10-07): run as few containers as possible for fast clone-to-running and small deployments. C4 L2 containers are logical runtime containers, not mandated deploy units.
<<<
COMMENT: >>>
KIND: requirement
BASE_UID: ARCH-DEPLOY-MINIMAL
VERSION_N: 0
priority: 5
iteration: iter-r0
security.catalog_ref: CM-2
security.verification_note: CM-2 baseline: one Dockerfile + role config is the deployable baseline; CM-7 roles off when not needed.
edge: ← uses from ARCH-AUTH-AS
edge: ← uses from ARCH-DEVENV-COMPOSE.1
edge: ← uses from ARCH-DEVENV-PARITY.1
edge: ← uses from ARCH-BUILD-FOUNDATION
edge: ← uses from FIX-ALLOW-DEVENV-MIN-CONTAINERS
edge: ← uses from FIX-ALLOW-APP-ROLE-SPLIT
edge: ← satisfies from CAP-DEVENV-DOCKERFILE-ROLES
edge: ← satisfies from CAP-SVC-STATIC-DEP-PATCH
edge: ← satisfies from CAP-DEVENV-LF-ENDINGS
in_scope_of_contract: ReqALM product (build)
delivered_by_release: R1 platform follow-ups (deferred from foundation PR)
edge: → conforms_to to CM-2 (pin imprint=nist-800-53@rev5-dogfood-20261006)
edge: → conforms_to to CM-7 (pin imprint=nist-800-53@rev5-dogfood-20261006)
<<<
RELATIONS:
- TYPE: Parent
  VALUE: SEC-DEVENV
- TYPE: Parent
  VALUE: ARCH-DEVENV-COMPOSE.1
  ROLE: Refines
- TYPE: Parent
  VALUE: ARCH-API
  ROLE: Uses
- TYPE: Parent
  VALUE: ARCH-UI
  ROLE: Uses
- TYPE: Parent
  VALUE: CAP-MCP-DESK
  ROLE: Uses
- TYPE: Parent
  VALUE: M04
  ROLE: Uses
- TYPE: Parent
  VALUE: CM-2
  ROLE: ConformsTo
- TYPE: Parent
  VALUE: CM-7
  ROLE: ConformsTo
- TYPE: Child
  VALUE: CONTRACT-ctr-reqalm-product
  ROLE: InScopeOf
- TYPE: Child
  VALUE: RELEASE-rel-r1-platform-followups
  ROLE: Delivers

[REQUIREMENT]
UID: ARCH-DEPLOY-PERIPHERALS
STATUS: Active
TITLE: Peripherals in as few containers as sensible (key store isolated in prod)
STATEMENT: >>>
Peripherals run in as few containers as is sensible. Dev/test: one peripherals container (Dockerfile peripherals target) runs Postgres and OpenBao under a lightweight supervisor, each with its own named volume. Co-locating them in dev is acceptable because dev keys are dev-only and protect no real data, and separate volumes keep reset and backup independent. Production: Postgres and OpenBao are separate deploy units with separate host, volume, and backup set. Rationale: envelope encryption protects data only if the KEK store does not share a compromise domain or backup set with the database whose DEKs it wraps (ARCH-KEY, SC-28(3)), and the two have different durability models (database backups/PITR versus OpenBao seal plus snapshots). SoftHSM2 is a PKCS#11 library loaded in-process, so it is not a peripheral container: it is an optional app hsm-test target and is never deployed. Reference topology: dev 2 containers (app + peripherals); prod 3 units (app, Postgres, OpenBao).
<<<
COMMENT: >>>
KIND: requirement
BASE_UID: ARCH-DEPLOY-PERIPHERALS
VERSION_N: 0
priority: 5
iteration: iter-r0
security.catalog_ref: SC-28.3
security.verification_note: SC-28(3) key storage separated from protected data in prod; CP-9 independent backups.
edge: ← uses from ARCH-DEVENV-KEYS
edge: ← uses from ARCH-DEVENV-COMPOSE.1
edge: ← uses from ARCH-DEVENV-MODES.1
edge: ← uses from ARCH-DEVENV-PARITY.1
edge: ← uses from FIX-ALLOW-DEVENV-MIN-CONTAINERS
edge: ← satisfies from CAP-DEVENV-PERIPHERALS
edge: ← satisfies from CAP-DEVENV-LF-ENDINGS
in_scope_of_contract: ReqALM product (build)
delivered_by_release: R1 platform follow-ups (deferred from foundation PR)
edge: → conforms_to to SC-28.3 (pin imprint=nist-800-53@rev5-dogfood-20261006)
edge: → conforms_to to SC-12 (pin imprint=nist-800-53@rev5-dogfood-20261006)
edge: → conforms_to to CP-9 (pin imprint=nist-800-53@rev5-dogfood-20261006)
<<<
RELATIONS:
- TYPE: Parent
  VALUE: SEC-DEVENV
- TYPE: Parent
  VALUE: ARCH-DEVENV-COMPOSE.1
  ROLE: Refines
- TYPE: Parent
  VALUE: ARCH-KEY
  ROLE: Uses
- TYPE: Parent
  VALUE: SC-28.3
  ROLE: ConformsTo
- TYPE: Parent
  VALUE: SC-12
  ROLE: ConformsTo
- TYPE: Parent
  VALUE: CP-9
  ROLE: ConformsTo
- TYPE: Child
  VALUE: CONTRACT-ctr-reqalm-product
  ROLE: InScopeOf
- TYPE: Child
  VALUE: RELEASE-rel-r1-platform-followups
  ROLE: Delivers

[REQUIREMENT]
UID: CAP-DEVENV-MONOREPO
STATUS: Active
TITLE: pnpm workspace monorepo (apps/reqalm + packages/intake)
STATEMENT: >>>
The repository is a pnpm workspace (pnpm-workspace.yaml: packages/*, apps/*) with one lockfile. The ReqAML platform app lives in apps/reqaml (@reqaml/app) and the SDoc Intake editor and CLI in packages/intake (sdoc-intake), so both build from one clone with `pnpm install`. Root scripts proxy per-package tasks (dev, dev:reqaml, build:cli, reqaml:migrate, reqaml:seed, devenv:smoke). Acceptance: `pnpm install --frozen-lockfile` succeeds on a clean clone; the editor still runs (`pnpm dev`) and builds (`pnpm build:cli`); the app typechecks and tests pass.
<<<
COMMENT: >>>
KIND: capability
BASE_UID: CAP-DEVENV-MONOREPO
VERSION_N: 0
priority: 10
iteration: iter-r0
security.catalog_ref: CM-2
security.verification_note: CM-2 baseline: one lockfile pins the supported toolchain. Verified 2026-10-07: pnpm install --frozen-lockfile; pnpm build:cli OK; editor dev server on :8087; sdoc-intake typecheck + 39/39 tests; @reqalm/app typecheck + tests.
in_scope_of_contract: ReqALM product (build)
delivered_by_release: PR #12 — devenv foundation
edge: → conforms_to to CM-2 (pin imprint=nist-800-53@rev5-dogfood-20261006)
<<<
RELATIONS:
- TYPE: Parent
  VALUE: SEC-DEVENV
- TYPE: Parent
  VALUE: ARCH-DEVENV-CLONE
  ROLE: Satisfies
- TYPE: Parent
  VALUE: CM-2
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-DEVENV-DOCKERFILE-ROLES
STATUS: Active
TITLE: Single Dockerfile; one app container with REQALM_ROLES toggles
STATEMENT: >>>
One multi-stage Dockerfile builds every image: app (Node 22, the deploy target), peripherals (dev/test only) and app-hsm-test. The app container runs one Node process whose roles are toggled by REQAML_ROLES (api, web, mcp, sync); /ready reports per enabled role, and routes for disabled roles are not mounted. Acceptance: the same image started with REQAML_ROLES=sync serves only probes (readiness lists sync only; /api and /mcp return 404) without a rebuild; with all roles it serves API, web, MCP stub and runs sync.
<<<
COMMENT: >>>
KIND: capability
BASE_UID: CAP-DEVENV-DOCKERFILE-ROLES
VERSION_N: 0
priority: 10
iteration: iter-r0
security.catalog_ref: CM-7
security.verification_note: CM-7 least functionality: disabled roles expose no endpoints. Verified 2026-10-07: docker compose build; REQALM_ROLES=sync run → /ready roles=[sync], /api/v1/seed/summary 404, POST /mcp 404, /health 200. Internal OAuth AS role not built yet (R1), so FIX-ALLOW-APP-ROLE-SPLIT is only partly exercised.
in_scope_of_contract: ReqALM product (build)
delivered_by_release: PR #12 — devenv foundation
edge: → conforms_to to CM-7 (pin imprint=nist-800-53@rev5-dogfood-20261006)
<<<
RELATIONS:
- TYPE: Parent
  VALUE: SEC-DEVENV
- TYPE: Parent
  VALUE: ARCH-DEPLOY-MINIMAL
  ROLE: Satisfies
- TYPE: Parent
  VALUE: ARCH-DEVENV-PARITY.1
  ROLE: Satisfies
- TYPE: Parent
  VALUE: FIX-ALLOW-APP-ROLE-SPLIT
  ROLE: Satisfies
- TYPE: Parent
  VALUE: CM-7
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-DEVENV-PERIPHERALS
STATUS: Active
TITLE: Dev peripherals container: Postgres + OpenBao
STATEMENT: >>>
The peripherals Dockerfile target runs Postgres 16 and OpenBao (checksum-verified release binary) in one dev/test container, each with its own named volume (reqaml-pg, reqaml-openbao) plus reqaml-secrets for the generated unseal key and root token. Its healthcheck passes only when Postgres accepts connections and OpenBao is initialized and unsealed. Acceptance: first start initializes both within seconds; restarting the container unseals OpenBao from the stored key and keeps data; production is documented as separate Postgres and OpenBao units.
<<<
COMMENT: >>>
KIND: capability
BASE_UID: CAP-DEVENV-PERIPHERALS
VERSION_N: 0
priority: 10
iteration: iter-r0
security.catalog_ref: SC-12
security.verification_note: SC-12 dev key material isolated in its own volume; never committed. Verified 2026-10-07: fresh start healthy; docker compose restart → unsealed and healthy, data kept. Production split (separate units) is a deploy concern not exercised here.
in_scope_of_contract: ReqALM product (build)
delivered_by_release: PR #12 — devenv foundation
edge: → conforms_to to SC-12 (pin imprint=nist-800-53@rev5-dogfood-20261006)
<<<
RELATIONS:
- TYPE: Parent
  VALUE: SEC-DEVENV
- TYPE: Parent
  VALUE: ARCH-DEPLOY-PERIPHERALS
  ROLE: Satisfies
- TYPE: Parent
  VALUE: ARCH-DEVENV-KEYS
  ROLE: Satisfies
- TYPE: Parent
  VALUE: SC-12
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-DEVENV-COMPOSE
STATUS: Active
TITLE: Clone-to-running Compose: full-container and hybrid modes
STATEMENT: >>>
docker-compose.yml defines the default 2-container stack (app + peripherals) from the one Dockerfile, with .env.example holding only safe dev defaults (empty OpenBao token, no dev password). Full-container: copy .env.example to .env and `docker compose up --build`. Hybrid: `docker compose up peripherals -d` then `pnpm dev:reqaml` (native tsx watch), which loads .env and takes the dev OpenBao token from the running peripherals container without writing it to disk. Acceptance: following the README from a clean clone yields a healthy app on :3000 with the seed loaded; `docker compose ps` shows exactly 2 containers; hybrid mode reaches /ready 200.
<<<
COMMENT: >>>
KIND: capability
BASE_UID: CAP-DEVENV-COMPOSE
VERSION_N: 0
priority: 10
iteration: iter-r0
security.catalog_ref: CM-2
security.verification_note: CM-2 / IA-5: no secrets in the repo; Compose is the documented baseline. Verified 2026-10-07: `pnpm devenv:smoke` from clean (no volumes, no .env) passed 2026-10-07; exactly 2 containers; hybrid mode /health, /ready, seed summary OK. Optional hsm-test Compose profile not yet wired.
in_scope_of_contract: ReqALM product (build)
delivered_by_release: PR #12 — devenv foundation
edge: → conforms_to to CM-2 (pin imprint=nist-800-53@rev5-dogfood-20261006)
<<<
RELATIONS:
- TYPE: Parent
  VALUE: SEC-DEVENV
- TYPE: Parent
  VALUE: ARCH-DEVENV-COMPOSE.1
  ROLE: Satisfies
- TYPE: Parent
  VALUE: ARCH-DEVENV-MODES.1
  ROLE: Satisfies
- TYPE: Parent
  VALUE: ARCH-DEVENV-CLONE
  ROLE: Satisfies
- TYPE: Parent
  VALUE: ARCH-DEVENV-SECRETS
  ROLE: Satisfies
- TYPE: Parent
  VALUE: FIX-ALLOW-DEVENV-MIN-CONTAINERS
  ROLE: Satisfies
- TYPE: Parent
  VALUE: CM-2
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-DEVENV-STARTUP-BACKOFF
STATUS: Active
TITLE: Startup backoff waiting for Postgres and OpenBao
STATEMENT: >>>
Before migrating or serving, the app waits for Postgres and a usable OpenBao with exponential backoff (1 s start, x1.5, capped at 15 s, up to REQAML_STARTUP_MAX_WAIT_MS = 120 s), then fails with a clear timeout. The pg pool survives server-side disconnects (idle-client errors are logged, not fatal). A dev-marked OpenBao in production is not retried; it goes straight to the self-check refusal. Acceptance: `docker compose restart` brings the stack back healthy with zero app container restarts, even while OpenBao is still sealed.
<<<
COMMENT: >>>
KIND: capability
BASE_UID: CAP-DEVENV-STARTUP-BACKOFF
VERSION_N: 0
priority: 10
iteration: iter-r0
security.catalog_ref: CP-10
security.verification_note: Recovery without crash-loops. Verified 2026-10-07: docker compose restart → app logged 'waiting for OpenBao: sealed' then healthy, RestartCount 0; unit tests for timeout and the production no-wait path.
in_scope_of_contract: ReqALM product (build)
delivered_by_release: PR #12 — devenv foundation
edge: → conforms_to to CP-10 (pin imprint=nist-800-53@rev5-dogfood-20261006)
<<<
RELATIONS:
- TYPE: Parent
  VALUE: SEC-DEVENV
- TYPE: Parent
  VALUE: ARCH-DEVENV-HEALTH
  ROLE: Satisfies
- TYPE: Parent
  VALUE: CP-10
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-PROD-SELFCHECK
STATUS: Active
TITLE: Production startup self-check refuses dev keys and dev accounts
STATEMENT: >>>
With REQAML_MODE=production the app refuses to start, with one explicit error listing every violation, when seeded dev local accounts exist, REQAML_SEED_ON_START or REQAML_DEV_ACCOUNT_PASSWORD is set, or OpenBao is dev-marked (dev address, REQAML_OPENBAO_DEV_MARKED, or the reqaml_dev marker on the Transit mount). The dev seed loader also exits non-zero in production. Acceptance: production mode against the dev stack exits 1 within about a second naming the dev accounts and dev OpenBao; no keys are unwrapped.
<<<
COMMENT: >>>
KIND: capability
BASE_UID: CAP-PROD-SELFCHECK
VERSION_N: 0
priority: 10
iteration: iter-r0
security.catalog_ref: CM-6
security.verification_note: CM-6 / IA-5: no default credentials in production. Verified 2026-10-07: docker compose run with REQALM_MODE=production → 'Startup self-check failed' (seeded dev accounts; dev-marked OpenBao / Transit mount), exit 1 in ~1 s; `REQALM_MODE=production pnpm reqalm:seed` refused. Dev-account login denial (FIX-DENY-DEVENV-PROD-LOGIN.1 (a)) needs the R1 internal AS.
in_scope_of_contract: ReqALM product (build)
delivered_by_release: PR #12 — devenv foundation
edge: → conforms_to to CM-6 (pin imprint=nist-800-53@rev5-dogfood-20261006)
<<<
RELATIONS:
- TYPE: Parent
  VALUE: SEC-DEVENV
- TYPE: Parent
  VALUE: ARCH-DEVENV-IDENTITY.1
  ROLE: Satisfies
- TYPE: Parent
  VALUE: ARCH-DEVENV-KEYS
  ROLE: Satisfies
- TYPE: Parent
  VALUE: FIX-DENY-DEV-KEK-IN-PROD
  ROLE: Satisfies
- TYPE: Parent
  VALUE: FIX-DENY-DEVENV-PROD-LOGIN.1
  ROLE: Satisfies
- TYPE: Parent
  VALUE: CM-6
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-DEVENV-OPENBAO-BOOTSTRAP
STATUS: Active
TITLE: Dev OpenBao Transit KEK bootstrap and round-trip
STATEMENT: >>>
On first start the peripherals container initializes OpenBao (1 key share, dev-only), stores the unseal key and root token in the reqaml-secrets volume, enables Transit with a reqaml_dev=true mount description, and creates the non-exportable aes256-gcm96 KEK reqaml-kek; later starts unseal from the stored key. The app proves the KEK works with a Transit encrypt/decrypt round-trip in /ready. Acceptance: fresh volumes initialize in seconds; /ready reports openbao ok only after a successful round-trip; restarts keep the KEK.
<<<
COMMENT: >>>
KIND: capability
BASE_UID: CAP-DEVENV-OPENBAO-BOOTSTRAP
VERSION_N: 0
priority: 10
iteration: iter-r0
security.catalog_ref: SC-12
security.verification_note: SC-12 / SC-28: dev KEK is dev-marked and refused in production. Verified 2026-10-07: init log 'dev-marked Transit mount, KEK reqaml-kek'; /ready openbao ok via round-trip; seal/unseal and restart tests. The pluggable KeyProvider API for app data (wrap/unwrap DEKs) is R1.
in_scope_of_contract: ReqALM product (build)
delivered_by_release: PR #12 — devenv foundation
edge: → conforms_to to SC-12 (pin imprint=nist-800-53@rev5-dogfood-20261006)
<<<
RELATIONS:
- TYPE: Parent
  VALUE: SEC-DEVENV
- TYPE: Parent
  VALUE: ARCH-DEVENV-KEYS
  ROLE: Satisfies
- TYPE: Parent
  VALUE: ARCH-KEY-PROVIDER
  ROLE: Satisfies
- TYPE: Parent
  VALUE: SC-12
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-DEVENV-MIGRATE-SEED
STATUS: Active
TITLE: Idempotent DB migrations and dogfood seed load
STATEMENT: >>>
SQL migrations (schema_migrations ledger, one transaction) run at startup and via `pnpm reqaml:migrate`; the dogfood seed (docs/design/seed/dogfood.yaml) loads on first start (REQAML_SEED_ON_START) and via `pnpm reqaml:seed` using insert-if-absent upserts, including releases and their delivers junction. Dev local accounts get a password from .env or one generated and printed once; no default credential is committed. Acceptance: re-running migrate and seed inserts zero rows and leaves counts unchanged; seed is refused in production.
<<<
COMMENT: >>>
KIND: capability
BASE_UID: CAP-DEVENV-MIGRATE-SEED
VERSION_N: 0
priority: 10
iteration: iter-r0
security.catalog_ref: CM-2
security.verification_note: Idempotent fixture load (FIX-ALLOW-DEVENV-SEED-IDEMPOTENT). Verified 2026-10-07: devenv smoke re-runs migrate + seed twice → 'Migrations up to date', inserted all 0, unchanged=true.
in_scope_of_contract: ReqALM product (build)
delivered_by_release: PR #12 — devenv foundation
edge: → conforms_to to CM-2 (pin imprint=nist-800-53@rev5-dogfood-20261006)
<<<
RELATIONS:
- TYPE: Parent
  VALUE: SEC-DEVENV
- TYPE: Parent
  VALUE: ARCH-DEVENV-SEED
  ROLE: Satisfies
- TYPE: Parent
  VALUE: FIX-ALLOW-DEVENV-SEED-IDEMPOTENT
  ROLE: Satisfies
- TYPE: Parent
  VALUE: CM-2
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-DEVENV-SMOKE
STATUS: Active
TITLE: Local devenv smoke harness; CI smoke is manual-only
STATEMENT: >>>
`pnpm devenv:smoke` is the primary dev-environment check: `docker compose up --build -d --wait`, /health, /ready and seed summary, migrate + seed re-run twice with no new rows, exactly 2 healthy containers, and production-mode refusal of the dev seed loader, dev accounts and dev OpenBao. Any failing command's stdout/stderr is printed, followed by `docker compose ps -a` and recent logs. The GitHub workflow runs only on workflow_dispatch to save Actions minutes. Acceptance: the smoke passes from a clean clone and a failure is diagnosable from its output alone.
<<<
COMMENT: >>>
KIND: capability
BASE_UID: CAP-DEVENV-SMOKE
VERSION_N: 0
priority: 10
iteration: iter-r0
security.catalog_ref: SA-11
security.verification_note: SA-11 developer testing. Verified 2026-10-07: `pnpm devenv:smoke` from clean (no volumes, no .env) passed 2026-10-07 (exit 0); forced failure (bad COMPOSE_FILE) printed the command stderr plus compose ps/logs.
in_scope_of_contract: ReqALM product (build)
delivered_by_release: PR #12 — devenv foundation
edge: → conforms_to to SA-11 (pin imprint=nist-800-53@rev5-dogfood-20261006)
<<<
RELATIONS:
- TYPE: Parent
  VALUE: SEC-DEVENV
- TYPE: Parent
  VALUE: FIX-ALLOW-DEVENV-SMOKE
  ROLE: Satisfies
- TYPE: Parent
  VALUE: FIX-ALLOW-DEVENV-SEED-IDEMPOTENT
  ROLE: Satisfies
- TYPE: Parent
  VALUE: FIX-ALLOW-DEVENV-MIN-CONTAINERS
  ROLE: Satisfies
- TYPE: Parent
  VALUE: SA-11
  ROLE: ConformsTo
- TYPE: Child
  VALUE: CONTRACT-ctr-reqalm-product
  ROLE: InScopeOf
- TYPE: Child
  VALUE: RELEASE-rel-pr12-devenv-foundation
  ROLE: Delivers

[REQUIREMENT]
UID: CAP-DEVENV-INIT
STATUS: Active
TITLE: Idempotent devenv:init secrets CLI
STATEMENT: >>>
`pnpm devenv:init` writes per-developer random secrets to gitignored `.reqaml/devenv.env` and merges root `.env` for Compose (Postgres password, dev account password, session/agent secrets). Reruns preserve values unless `--rotate`. No fixed default passwords in the repo.
<<<
COMMENT: >>>
KIND: capability
BASE_UID: CAP-DEVENV-INIT
VERSION_N: 0
priority: 10
iteration: iter-r1
security.catalog_ref: IA-5
security.verification_note: IA-5 dev credential hygiene. Verified: Local Docker 2026-10-07 on PR #13 follow-up (6a5f0db + verification fixes), fresh volumes: `pnpm devenv:init` idempotent (byte-identical rerun), `--rotate` issues new secrets (needs `down -v` for the Postgres volume), secrets files mode 600 and gitignored; `docker compose up --build -d --wait` with and without the hostports overlay (app 127.0.0.1:3000 only; peripherals unpublished without the overlay, loopback-only with it); /ready all green, restart count 0; `pnpm devenv:smoke` pass incl. auth-flow-smoke (server-side OAuth handoffs, PKCE S256, refresh rotation/reuse family revoke, RFC7009 refresh+access revoke, lockout + username normalize, Reader RBAC 403, wrong audience 401 at MCP, upstream connectors 401 unauthenticated, session cookie HttpOnly+SameSite=Lax, cookie mutation without CSRF 401, signout ends session, sam-security MFA login via `devenv:mfa`, TOTP replay rejected (and one wrong code does not lock the account), agent tokens default Reader / Author max / Developer+ refused, TTL <= 1h, agent token revoked 401), auth_audit_events incl. agent-attributed mutation, IP throttle 200 -> 401 after 20 failures, production refused dev accounts/keys, missing REQALM_ISSUER_URL and blanket trustProxy; headless Chrome first-login TOTP enrollment (jamie-ao) then MFA re-login; `@reqalm/app` test 30/30, typecheck pass; seed yaml_to_strictdoc --validate pass.
in_scope_of_contract: ReqALM product (build)
delivered_by_release: R1 — foundation shell + internal auth
edge: → conforms_to to IA-5 (pin imprint=nist-800-53@rev5-dogfood-20261006)
<<<
RELATIONS:
- TYPE: Parent
  VALUE: SEC-DEVENV
- TYPE: Parent
  VALUE: ARCH-DEVENV-SECRETS
  ROLE: Satisfies
- TYPE: Parent
  VALUE: ARCH-DEVENV-IDENTITY.1
  ROLE: Satisfies
- TYPE: Parent
  VALUE: IA-5
  ROLE: ConformsTo
- TYPE: Child
  VALUE: CONTRACT-ctr-reqalm-product
  ROLE: InScopeOf
- TYPE: Child
  VALUE: RELEASE-rel-r1-foundation-shell-auth
  ROLE: Delivers

[REQUIREMENT]
UID: CAP-TEST-PGLITE-DB
STATUS: Active
TITLE: In-process Postgres (PGlite) with real migrations
STATEMENT: >>>
Integration tests use `@electric-sql/pglite` with the same migration SQL files as production (`apps/reqaml/src/db/migrations/*.sql`) via `runMigrationsOnPglite`.
<<<
COMMENT: >>>
KIND: capability
BASE_UID: CAP-TEST-PGLITE-DB
VERSION_N: 0
priority: 10
iteration: iter-r1
security.catalog_ref: CM-2
security.verification_note: Isolated WASM DB; no committed secrets.
in_scope_of_contract: ReqALM product (build)
delivered_by_release: R1 — in-process test harness (no Docker)
<<<
RELATIONS:
- TYPE: Parent
  VALUE: SEC-DEVENV
- TYPE: Parent
  VALUE: ARCH-BUILD-FOUNDATION
  ROLE: Satisfies
- TYPE: Child
  VALUE: CONTRACT-ctr-reqalm-product
  ROLE: InScopeOf
- TYPE: Child
  VALUE: RELEASE-rel-r1-test-harness
  ROLE: Delivers

[REQUIREMENT]
UID: CAP-TEST-PNPM-GATE
STATUS: Active
TITLE: Docker-free `pnpm test` gate
STATEMENT: >>>
Root `pnpm test` runs package unit tests plus the in-process auth harness; contributors and cloud agents run it before push. Full stack checks remain `pnpm devenv:smoke` (Docker, maintainer-local).
<<<
COMMENT: >>>
KIND: capability
BASE_UID: CAP-TEST-PNPM-GATE
VERSION_N: 0
priority: 10
iteration: iter-r1
security.catalog_ref: CM-2
security.verification_note: Fast feedback without containers. Verified: 2026-10-07 cloud agent VM (no Docker): `pnpm test` pass — @reqalm/app 38/38 incl. auth.integration.test.ts (8 in-process Fastify inject cases: PKCE/redirect_uri, refresh reuse, lockout, IP throttle failures-only, TOTP replay, CSRF cookie mutations, agent token roles/TTL/audience); PGlite runs real SQL migrations; createMemoryKeyProvider wrap/unwrap; typecheck pass.
in_scope_of_contract: ReqALM product (build)
delivered_by_release: R1 — in-process test harness (no Docker)
<<<
RELATIONS:
- TYPE: Parent
  VALUE: SEC-DEVENV
- TYPE: Parent
  VALUE: FIX-ALLOW-DEVENV-SMOKE
  ROLE: Satisfies
- TYPE: Child
  VALUE: CONTRACT-ctr-reqalm-product
  ROLE: InScopeOf
- TYPE: Child
  VALUE: RELEASE-rel-r1-test-harness
  ROLE: Delivers

[REQUIREMENT]
UID: CAP-DEVENV-SMOKE-COMPOSE-ISOLATION
STATUS: Active
TITLE: devenv:smoke pins Compose project name
STATEMENT: >>>
`pnpm devenv:smoke` sets `COMPOSE_PROJECT_NAME` (default `sdoc-intake-dev`, overridable) on every Compose invocation, logs the hostports overlay, and clears the loopback IP-throttle row before its throttle check so reruns against a running dev stack are repeatable.
<<<
COMMENT: >>>
KIND: capability
BASE_UID: CAP-DEVENV-SMOKE-COMPOSE-ISOLATION
VERSION_N: 0
priority: 10
iteration: iter-r1
security.catalog_ref: CM-2
security.verification_note: Verified: 2026-10-07 local Docker (maintainer box): `pnpm devenv:smoke` with COMPOSE_PROJECT_NAME unset used project sdoc-intake-dev (no second stack), logged the overlay, and passed on a reused volume incl. IP throttle 200 -> 401.
in_scope_of_contract: ReqALM product (build)
delivered_by_release: R1 — test/build hygiene (Docker-free test follow-ups)
<<<
RELATIONS:
- TYPE: Parent
  VALUE: SEC-DEVENV
- TYPE: Parent
  VALUE: FIX-ALLOW-DEVENV-SMOKE
  ROLE: Satisfies
- TYPE: Child
  VALUE: CONTRACT-ctr-reqalm-product
  ROLE: InScopeOf
- TYPE: Child
  VALUE: RELEASE-rel-r1-test-hygiene
  ROLE: Delivers

[REQUIREMENT]
UID: CAP-DEVENV-SEED-RESET
STATUS: Active
TITLE: Dev-only dogfood seed reset (pnpm devenv:seed:reset)
STATEMENT: >>>
Development-only command `pnpm devenv:seed:reset --confirm` wipes ReqALM project fixture rows (requirement lines/versions, releases and delivers) and reloads them from docs/design/seed/dogfood.yaml in one transaction (any load failure rolls back), preserving identities, grants, local accounts, sessions/MFA, OpenBao keys, and append-only audit_events; identities and grants are only inserted when missing, never rewritten or re-activated. Runs only when the environment positively identifies as local devenv (REQALM_MODE=development, .reqalm/devenv.env present, NODE_ENV not production, and DATABASE_URL resolving to 127.0.0.1 or localhost port 5432 including ?host=/?port= overrides); no environment variable relaxes these checks. Requires explicit --confirm; --dry-run prints the plan read-only. Records one devenv.seed.reset business audit event with wipe/load counts and an unverified CLI actor label, attributed to no ReqALM identity. Idempotent second run yields identical DB contents.
<<<
COMMENT: >>>
KIND: capability
BASE_UID: CAP-DEVENV-SEED-RESET
VERSION_N: 0
priority: 10
iteration: iter-r1
security.catalog_ref: CM-2
security.verification_note: Planned until seed-reset PR merges and is verified locally.
in_scope_of_contract: ReqALM product (build)
delivered_by_release: R1 — dev dogfood seed reset (pnpm devenv:seed:reset)
<<<
RELATIONS:
- TYPE: Parent
  VALUE: SEC-DEVENV
- TYPE: Parent
  VALUE: ARCH-DEVENV-SEED
  ROLE: Satisfies
- TYPE: Parent
  VALUE: FIX-ALLOW-DEVENV-SEED-IDEMPOTENT
  ROLE: Satisfies
- TYPE: Child
  VALUE: CONTRACT-ctr-reqalm-product
  ROLE: InScopeOf
- TYPE: Child
  VALUE: RELEASE-rel-r1-seed-reset
  ROLE: Delivers

[[/SECTION]]

[[SECTION]]
UID: SEC-BUILD
TITLE: Build sequencing

[TEXT]
UID: SEC-BUILD-INTRO
STATEMENT: >>>
Build sequencing for ReqAML implementation. This is ordering only: it does not cut v1 scope or mark any requirement out of scope.
<<<

[REQUIREMENT]
UID: ARCH-BUILD-FOUNDATION
STATUS: Active
TITLE: Foundation slice first: platform shell + authentication + key store
STATEMENT: >>>
The first implementation slice is the foundation: platform shell (App shell, routes and guards, layout: ARCH-UI / ARCH-UI-GUARD), API layering and OpenAPI (ARCH-API / ARCH-API-LAYERS), tenancy scope (ARCH-CP-SCOPE), internal OAuth AS (ARCH-AUTH-*), local accounts and credential store (ARCH-CRED-*), key / secret store with OpenBao (ARCH-KEY-*), RBAC enforcement points (ARCH-API-RBAC / CAP-RBAC), audit (ARCH-OTEL / ARCH-CRED-AUDIT), health (M04), and the minimal-container Compose environment (ARCH-DEVENV-*, ARCH-DEPLOY-*). All other requirements layer on this foundation. This records build order only: no v1 requirement is deferred, descoped, or marked out of scope. Planned release rel-r1-foundation-shell-auth tracks the slice.
<<<
COMMENT: >>>
KIND: requirement
BASE_UID: ARCH-BUILD-FOUNDATION
VERSION_N: 0
priority: 1
iteration: iter-r1
security.catalog_ref: SA-8
security.verification_note: SA-8 security engineering: security foundations built first.
edge: ← satisfies from CAP-TEST-PGLITE-DB
edge: ← satisfies from CAP-TEST-PROD-BUILD-EXCLUDE
edge: ← satisfies from CAP-RENAME-REQALM
edge: ← refines from ARCH-TEST-HARNESS-TEARDOWN
in_scope_of_contract: ReqALM product (build)
delivered_by_release: R1 — foundation shell + internal auth
edge: → conforms_to to SA-8 (pin imprint=nist-800-53@rev5-dogfood-20261006)
<<<
RELATIONS:
- TYPE: Parent
  VALUE: SEC-BUILD
- TYPE: Parent
  VALUE: ARCH-UI
  ROLE: Uses
- TYPE: Parent
  VALUE: ARCH-API
  ROLE: Uses
- TYPE: Parent
  VALUE: ARCH-CP-SCOPE
  ROLE: Uses
- TYPE: Parent
  VALUE: ARCH-AUTH-AS
  ROLE: Uses
- TYPE: Parent
  VALUE: ARCH-CRED
  ROLE: Uses
- TYPE: Parent
  VALUE: ARCH-KEY
  ROLE: Uses
- TYPE: Parent
  VALUE: ARCH-API-RBAC
  ROLE: Uses
- TYPE: Parent
  VALUE: ARCH-OTEL
  ROLE: Uses
- TYPE: Parent
  VALUE: M04
  ROLE: Uses
- TYPE: Parent
  VALUE: ARCH-DEVENV-COMPOSE.1
  ROLE: Uses
- TYPE: Parent
  VALUE: ARCH-DEPLOY-MINIMAL
  ROLE: Uses
- TYPE: Parent
  VALUE: SA-8
  ROLE: ConformsTo
- TYPE: Parent
  VALUE: ARCH-AUTH-MCP-REQUIRED
  ROLE: Uses
- TYPE: Parent
  VALUE: ARCH-AUTH-PROFILE
  ROLE: Uses
- TYPE: Child
  VALUE: CONTRACT-ctr-reqalm-product
  ROLE: InScopeOf
- TYPE: Child
  VALUE: RELEASE-rel-r1-foundation-shell-auth
  ROLE: Delivers

[REQUIREMENT]
UID: CAP-TEST-PROD-BUILD-EXCLUDE
STATUS: Active
TITLE: Production build excludes test harness modules
STATEMENT: >>>
TypeScript production build (`tsconfig.build.json`) excludes `src/test/**` and `src/key/memory-provider.ts`; tests import the in-memory KeyProvider from its own module. Docker `dist/` contains no test harness or fake key files.
<<<
COMMENT: >>>
KIND: capability
BASE_UID: CAP-TEST-PROD-BUILD-EXCLUDE
VERSION_N: 0
priority: 10
iteration: iter-r1
security.catalog_ref: CM-2
security.verification_note: Verified: 2026-10-07 cloud agent VM (no Docker): `pnpm test` pass (@reqalm/app 39/39); `pnpm typecheck` pass; `pnpm --filter @reqalm/app build` dist has no `dist/test/**` or `dist/key/memory-provider.js`.
in_scope_of_contract: ReqALM product (build)
delivered_by_release: R1 — test/build hygiene (Docker-free test follow-ups)
<<<
RELATIONS:
- TYPE: Parent
  VALUE: SEC-BUILD
- TYPE: Parent
  VALUE: ARCH-KEY-PROVIDER
  ROLE: Satisfies
- TYPE: Parent
  VALUE: ARCH-BUILD-FOUNDATION
  ROLE: Satisfies
- TYPE: Child
  VALUE: CONTRACT-ctr-reqalm-product
  ROLE: InScopeOf
- TYPE: Child
  VALUE: RELEASE-rel-r1-test-hygiene
  ROLE: Delivers

[REQUIREMENT]
UID: CAP-RENAME-REQALM
STATUS: Active
TITLE: Product name correction: ReqALM (ALM, not AML)
STATEMENT: >>>
Repository, runtime identifiers, OAuth client IDs, env vars, and dogfood seed use the product name ReqALM (requirements + application lifecycle management). Persisted identifiers keep the legacy ReqAML spelling where renaming would orphan existing data: Compose volume names (reqaml-pg, reqaml-openbao, reqaml-secrets), OpenBao Transit key names (reqaml-kek, reqaml-dek-*) and an existing Postgres role/database. Existing dev stacks upgrade in place: migration 005 renames OAuth client ids, the project id and seeded grant ids, and `pnpm devenv:init` migrates .reqaml/ and REQAML_* names keeping secret values. Active requirement statements keep historical ReqAML prose until a content successor.
<<<
COMMENT: >>>
KIND: capability
BASE_UID: CAP-RENAME-REQALM
VERSION_N: 0
priority: 10
iteration: iter-r1
security.catalog_ref: CM-2
security.verification_note: Verified 2026-10-07: offline `pnpm test` 39/39 + 209/209, `pnpm typecheck`, `pnpm build` pass; seed yaml_to_strictdoc --validate pass. Local Docker in-place upgrade of a PR #15 dev stack (same volumes): `pnpm devenv:init` moved .reqaml/ + REQAML_* to .reqalm/ + REQALM_* with byte-identical secret values; migration 005 renamed OAuth client ids, the project id and seeded grant ids; /ready green, 0 restarts; the existing dev password and sam-security MFA secret still sign in; UI says ReqALM; `pnpm devenv:smoke` pass.
in_scope_of_contract: ReqALM product (build)
delivered_by_release: R1 — product rename ReqALM
<<<
RELATIONS:
- TYPE: Parent
  VALUE: SEC-BUILD
- TYPE: Parent
  VALUE: ARCH-BUILD-FOUNDATION
  ROLE: Satisfies
- TYPE: Child
  VALUE: CONTRACT-ctr-reqalm-product
  ROLE: InScopeOf
- TYPE: Child
  VALUE: RELEASE-rel-r1-rename-reqalm
  ROLE: Delivers

[REQUIREMENT]
UID: ARCH-TEST-HARNESS-TEARDOWN
STATUS: Active
TITLE: createTestApp closes DB on setup failure
STATEMENT: >>>
createTestApp (in-process harness) shall close the database pool when setup throws so PGlite/file-backed tests do not leak handles between cases.
<<<
COMMENT: >>>
KIND: requirement
BASE_UID: ARCH-TEST-HARNESS-TEARDOWN
VERSION_N: 0
priority: 15
iteration: iter-r1
security.catalog_ref: CM-2
security.verification_note: Groomed 2026-10-09; pre-write or UI track.
in_scope_of_contract: ReqALM product (build)
<<<
RELATIONS:
- TYPE: Parent
  VALUE: SEC-BUILD
- TYPE: Parent
  VALUE: ARCH-BUILD-FOUNDATION
  ROLE: Refines
- TYPE: Child
  VALUE: CONTRACT-ctr-reqalm-product
  ROLE: InScopeOf

[[/SECTION]]
