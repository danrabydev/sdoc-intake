[DOCUMENT]
TITLE: ReqALM — Contracts & Releases
UID: reqalm-contracts-releases
VERSION: 2026-10-07
OPTIONS:
  MARKUP: Text
METADATA:
  client: Raby-Family (raby-family)
  project: ReqALM (reqalm)
  schema_version: 2026-10-07
  note: ReqALM dogfood export — StrictDoc interchange only
  export_kind: contracts-releases
  tree_note: junction entities; not tree parents

[GRAMMAR]
ELEMENTS:
- TAG: TEXT
  FIELDS:
  - TITLE: UID
    TYPE: String
    REQUIRED: False
  - TITLE: STATEMENT
    TYPE: String
    REQUIRED: True
- TAG: REQUIREMENT
  FIELDS:
  - TITLE: UID
    TYPE: String
    REQUIRED: True
  - TITLE: STATUS
    TYPE: String
    REQUIRED: False
  - TITLE: TITLE
    TYPE: String
    REQUIRED: False
  - TITLE: STATEMENT
    TYPE: String
    REQUIRED: True
  - TITLE: COMMENT
    TYPE: String
    REQUIRED: False
  RELATIONS:
  - TYPE: Parent
  - TYPE: Parent
    ROLE: Satisfies
  - TYPE: Parent
    ROLE: ConformsTo
  - TYPE: Parent
    ROLE: Uses
  - TYPE: Parent
    ROLE: Refines
  - TYPE: Parent
    ROLE: InScopeOf
    REVERSE_ROLE: InScopeOf
  - TYPE: Parent
    ROLE: Delivers
    REVERSE_ROLE: Delivers
  - TYPE: Child
  - TYPE: Child
    ROLE: Satisfies
  - TYPE: Child
    ROLE: ConformsTo
  - TYPE: Child
    ROLE: Uses
  - TYPE: Child
    ROLE: Refines
  - TYPE: Child
    ROLE: InScopeOf
  - TYPE: Child
    ROLE: Delivers
  - TYPE: File

[[SECTION]]
UID: SEC-CONTRACTS-EXPORT
TITLE: Contracts

[REQUIREMENT]
UID: CONTRACT-contract-design-2026-10
STATUS: Active
TITLE: Contract Design-2026-10
STATEMENT: >>>
ReqALM contract overlay `Design-2026-10` (status=active, starts_on=2026-10-06). Links requirement versions via in_scope_of; not a tree parent.
<<<
COMMENT: >>>
KIND: contract
contract_id: contract-design-2026-10
client_id: raby-family
project_id: reqalm
in_scope_of: A01, A02, A03, A04, A05, A06, A07, A08, A09, A10, A11, A12.1, B01, B04, B07, B08, C01, C03, C06, C08, D01, D02, D03, D04, D06, E01, E02, E04, F01, F04, F07, F10, G01, G03, G05, G08, H06, H09, I01, I03, ARCH-CP-HIER, ARCH-CP-SCOPE, ARCH-V...
in_scope_of_count: 63
covers_releases: (none)
covers_releases_count: 0
<<<
RELATIONS:
- TYPE: Parent
  VALUE: SEC-CONTRACTS-EXPORT
- TYPE: Parent
  VALUE: A01
  ROLE: InScopeOf
- TYPE: Parent
  VALUE: A02
  ROLE: InScopeOf
- TYPE: Parent
  VALUE: A03
  ROLE: InScopeOf
- TYPE: Parent
  VALUE: A04
  ROLE: InScopeOf
- TYPE: Parent
  VALUE: A05
  ROLE: InScopeOf
- TYPE: Parent
  VALUE: A06
  ROLE: InScopeOf
- TYPE: Parent
  VALUE: A07
  ROLE: InScopeOf
- TYPE: Parent
  VALUE: A08
  ROLE: InScopeOf
- TYPE: Parent
  VALUE: A09
  ROLE: InScopeOf
- TYPE: Parent
  VALUE: A10
  ROLE: InScopeOf
- TYPE: Parent
  VALUE: A11
  ROLE: InScopeOf
- TYPE: Parent
  VALUE: A12.1
  ROLE: InScopeOf
- TYPE: Parent
  VALUE: B01
  ROLE: InScopeOf
- TYPE: Parent
  VALUE: B04
  ROLE: InScopeOf
- TYPE: Parent
  VALUE: B07
  ROLE: InScopeOf
- TYPE: Parent
  VALUE: B08
  ROLE: InScopeOf
- TYPE: Parent
  VALUE: C01
  ROLE: InScopeOf
- TYPE: Parent
  VALUE: C03
  ROLE: InScopeOf
- TYPE: Parent
  VALUE: C06
  ROLE: InScopeOf
- TYPE: Parent
  VALUE: C08
  ROLE: InScopeOf
- TYPE: Parent
  VALUE: D01
  ROLE: InScopeOf
- TYPE: Parent
  VALUE: D02
  ROLE: InScopeOf
- TYPE: Parent
  VALUE: D03
  ROLE: InScopeOf
- TYPE: Parent
  VALUE: D04
  ROLE: InScopeOf
- TYPE: Parent
  VALUE: D06
  ROLE: InScopeOf
- TYPE: Parent
  VALUE: E01
  ROLE: InScopeOf
- TYPE: Parent
  VALUE: E02
  ROLE: InScopeOf
- TYPE: Parent
  VALUE: E04
  ROLE: InScopeOf
- TYPE: Parent
  VALUE: F01
  ROLE: InScopeOf
- TYPE: Parent
  VALUE: F04
  ROLE: InScopeOf
- TYPE: Parent
  VALUE: F07
  ROLE: InScopeOf
- TYPE: Parent
  VALUE: F10
  ROLE: InScopeOf
- TYPE: Parent
  VALUE: G01
  ROLE: InScopeOf
- TYPE: Parent
  VALUE: G03
  ROLE: InScopeOf
- TYPE: Parent
  VALUE: G05
  ROLE: InScopeOf
- TYPE: Parent
  VALUE: G08
  ROLE: InScopeOf
- TYPE: Parent
  VALUE: H06
  ROLE: InScopeOf
- TYPE: Parent
  VALUE: H09
  ROLE: InScopeOf
- TYPE: Parent
  VALUE: I01
  ROLE: InScopeOf
- TYPE: Parent
  VALUE: I03
  ROLE: InScopeOf
- TYPE: Parent
  VALUE: ARCH-CP-HIER
  ROLE: InScopeOf
- TYPE: Parent
  VALUE: ARCH-CP-SCOPE
  ROLE: InScopeOf
- TYPE: Parent
  VALUE: ARCH-VER
  ROLE: InScopeOf
- TYPE: Parent
  VALUE: ARCH-VER-SUCC
  ROLE: InScopeOf
- TYPE: Parent
  VALUE: ARCH-CONTRACT.1
  ROLE: InScopeOf
- TYPE: Parent
  VALUE: ARCH-CONTRACT-DOC
  ROLE: InScopeOf
- TYPE: Parent
  VALUE: ARCH-RELEASE
  ROLE: InScopeOf
- TYPE: Parent
  VALUE: ARCH-RELEASE-FREEZE
  ROLE: InScopeOf
- TYPE: Parent
  VALUE: ARCH-UI
  ROLE: InScopeOf
- TYPE: Parent
  VALUE: ARCH-UI-GUARD
  ROLE: InScopeOf
- TYPE: Parent
  VALUE: ARCH-API
  ROLE: InScopeOf
- TYPE: Parent
  VALUE: ARCH-API-RBAC
  ROLE: InScopeOf
- TYPE: Parent
  VALUE: ARCH-API-LAYERS
  ROLE: InScopeOf
- TYPE: Parent
  VALUE: ARCH-OTEL
  ROLE: InScopeOf
- TYPE: Parent
  VALUE: CAP-SSO
  ROLE: InScopeOf
- TYPE: Parent
  VALUE: CAP-SCOPED-VIEW
  ROLE: InScopeOf
- TYPE: Parent
  VALUE: CAP-RBAC
  ROLE: InScopeOf
- TYPE: Parent
  VALUE: CAP-TREE
  ROLE: InScopeOf
- TYPE: Parent
  VALUE: CAP-CONTRACT-UI
  ROLE: InScopeOf
- TYPE: Parent
  VALUE: CAP-VERSION-UI
  ROLE: InScopeOf
- TYPE: Parent
  VALUE: MC01.1
  ROLE: InScopeOf
- TYPE: Parent
  VALUE: MC02
  ROLE: InScopeOf
- TYPE: Parent
  VALUE: MC03
  ROLE: InScopeOf

[REQUIREMENT]
UID: CONTRACT-contract-security-package
STATUS: Active
TITLE: Contract Security package
STATEMENT: >>>
ReqALM contract overlay `Security package` (status=active, starts_on=2026-10-06). Links requirement versions via in_scope_of; not a tree parent.
<<<
COMMENT: >>>
KIND: contract
contract_id: contract-security-package
client_id: raby-family
project_id: reqalm
in_scope_of: A01, A02, A03, A04, A06, A07, A08, A09, A10, A11, A12.1, ARCH-CP-SCOPE, ARCH-API-RBAC, ARCH-OTEL, ARCH-UI-GUARD, CAP-SSO, CAP-SCOPED-VIEW, CAP-RBAC, CAP-MCP-DESK, CAP-AUDIT, MC01.1, MC02, MC03, M01, M02, M03, D11, H06
in_scope_of_count: 28
covers_releases: (none)
covers_releases_count: 0
<<<
RELATIONS:
- TYPE: Parent
  VALUE: SEC-CONTRACTS-EXPORT
- TYPE: Parent
  VALUE: A01
  ROLE: InScopeOf
- TYPE: Parent
  VALUE: A02
  ROLE: InScopeOf
- TYPE: Parent
  VALUE: A03
  ROLE: InScopeOf
- TYPE: Parent
  VALUE: A04
  ROLE: InScopeOf
- TYPE: Parent
  VALUE: A06
  ROLE: InScopeOf
- TYPE: Parent
  VALUE: A07
  ROLE: InScopeOf
- TYPE: Parent
  VALUE: A08
  ROLE: InScopeOf
- TYPE: Parent
  VALUE: A09
  ROLE: InScopeOf
- TYPE: Parent
  VALUE: A10
  ROLE: InScopeOf
- TYPE: Parent
  VALUE: A11
  ROLE: InScopeOf
- TYPE: Parent
  VALUE: A12.1
  ROLE: InScopeOf
- TYPE: Parent
  VALUE: ARCH-CP-SCOPE
  ROLE: InScopeOf
- TYPE: Parent
  VALUE: ARCH-API-RBAC
  ROLE: InScopeOf
- TYPE: Parent
  VALUE: ARCH-OTEL
  ROLE: InScopeOf
- TYPE: Parent
  VALUE: ARCH-UI-GUARD
  ROLE: InScopeOf
- TYPE: Parent
  VALUE: CAP-SSO
  ROLE: InScopeOf
- TYPE: Parent
  VALUE: CAP-SCOPED-VIEW
  ROLE: InScopeOf
- TYPE: Parent
  VALUE: CAP-RBAC
  ROLE: InScopeOf
- TYPE: Parent
  VALUE: CAP-MCP-DESK
  ROLE: InScopeOf
- TYPE: Parent
  VALUE: CAP-AUDIT
  ROLE: InScopeOf
- TYPE: Parent
  VALUE: MC01.1
  ROLE: InScopeOf
- TYPE: Parent
  VALUE: MC02
  ROLE: InScopeOf
- TYPE: Parent
  VALUE: MC03
  ROLE: InScopeOf
- TYPE: Parent
  VALUE: M01
  ROLE: InScopeOf
- TYPE: Parent
  VALUE: M02
  ROLE: InScopeOf
- TYPE: Parent
  VALUE: M03
  ROLE: InScopeOf
- TYPE: Parent
  VALUE: D11
  ROLE: InScopeOf
- TYPE: Parent
  VALUE: H06
  ROLE: InScopeOf

[REQUIREMENT]
UID: CONTRACT-contract-platform-baseline
STATUS: Active
TITLE: Contract Platform baseline
STATEMENT: >>>
ReqALM contract overlay `Platform baseline` (status=active, starts_on=2026-10-01). Links requirement versions via in_scope_of; not a tree parent.
<<<
COMMENT: >>>
KIND: contract
contract_id: contract-platform-baseline
client_id: raby-family
project_id: reqalm
in_scope_of: A01, A03, B04, B07, B08, C01, C06, D01, D02, D03, D04, ARCH-CP-HIER, ARCH-VER, ARCH-API, ARCH-API-LAYERS, ARCH-UI, CAP-SSO, CAP-SCOPED-VIEW, CAP-RBAC, CAP-TREE, L02, M04, N01
in_scope_of_count: 23
covers_releases: (none)
covers_releases_count: 0
<<<
RELATIONS:
- TYPE: Parent
  VALUE: SEC-CONTRACTS-EXPORT
- TYPE: Parent
  VALUE: A01
  ROLE: InScopeOf
- TYPE: Parent
  VALUE: A03
  ROLE: InScopeOf
- TYPE: Parent
  VALUE: B04
  ROLE: InScopeOf
- TYPE: Parent
  VALUE: B07
  ROLE: InScopeOf
- TYPE: Parent
  VALUE: B08
  ROLE: InScopeOf
- TYPE: Parent
  VALUE: C01
  ROLE: InScopeOf
- TYPE: Parent
  VALUE: C06
  ROLE: InScopeOf
- TYPE: Parent
  VALUE: D01
  ROLE: InScopeOf
- TYPE: Parent
  VALUE: D02
  ROLE: InScopeOf
- TYPE: Parent
  VALUE: D03
  ROLE: InScopeOf
- TYPE: Parent
  VALUE: D04
  ROLE: InScopeOf
- TYPE: Parent
  VALUE: ARCH-CP-HIER
  ROLE: InScopeOf
- TYPE: Parent
  VALUE: ARCH-VER
  ROLE: InScopeOf
- TYPE: Parent
  VALUE: ARCH-API
  ROLE: InScopeOf
- TYPE: Parent
  VALUE: ARCH-API-LAYERS
  ROLE: InScopeOf
- TYPE: Parent
  VALUE: ARCH-UI
  ROLE: InScopeOf
- TYPE: Parent
  VALUE: CAP-SSO
  ROLE: InScopeOf
- TYPE: Parent
  VALUE: CAP-SCOPED-VIEW
  ROLE: InScopeOf
- TYPE: Parent
  VALUE: CAP-RBAC
  ROLE: InScopeOf
- TYPE: Parent
  VALUE: CAP-TREE
  ROLE: InScopeOf
- TYPE: Parent
  VALUE: L02
  ROLE: InScopeOf
- TYPE: Parent
  VALUE: M04
  ROLE: InScopeOf
- TYPE: Parent
  VALUE: N01
  ROLE: InScopeOf

[REQUIREMENT]
UID: CONTRACT-contract-legacy-intake-closed
STATUS: Draft
TITLE: Contract Legacy intake (closed)
STATEMENT: >>>
ReqALM contract overlay `Legacy intake (closed)` (status=closed, starts_on=2026-09-01). Links requirement versions via in_scope_of; not a tree parent.
<<<
COMMENT: >>>
KIND: contract
contract_id: contract-legacy-intake-closed
client_id: raby-family
project_id: reqalm
in_scope_of: A01, ARCH-CONTRACT, FIX-SUCC-2HOP.1
in_scope_of_count: 3
covers_releases: (none)
covers_releases_count: 0
<<<
RELATIONS:
- TYPE: Parent
  VALUE: SEC-CONTRACTS-EXPORT
- TYPE: Parent
  VALUE: A01
  ROLE: InScopeOf
- TYPE: Parent
  VALUE: ARCH-CONTRACT
  ROLE: InScopeOf
- TYPE: Parent
  VALUE: FIX-SUCC-2HOP.1
  ROLE: InScopeOf

[REQUIREMENT]
UID: CONTRACT-contract-fixture-doc-walk
STATUS: Active
TITLE: Contract Fixture doc-walk
STATEMENT: >>>
ReqALM contract overlay `Fixture doc-walk` (status=active, starts_on=2026-10-06). Links requirement versions via in_scope_of; not a tree parent.
<<<
COMMENT: >>>
KIND: contract
contract_id: contract-fixture-doc-walk
client_id: raby-family
project_id: reqalm
in_scope_of: A01, A02
in_scope_of_count: 2
covers_releases: (none)
covers_releases_count: 0
<<<
RELATIONS:
- TYPE: Parent
  VALUE: SEC-CONTRACTS-EXPORT
- TYPE: Parent
  VALUE: A01
  ROLE: InScopeOf
- TYPE: Parent
  VALUE: A02
  ROLE: InScopeOf

[REQUIREMENT]
UID: CONTRACT-ctr-reqalm-product
STATUS: Active
TITLE: Contract ReqALM product (build)
STATEMENT: >>>
ReqALM contract overlay `ReqALM product (build)` (status=active, starts_on=2026-10-01). Links requirement versions via in_scope_of; not a tree parent.
<<<
COMMENT: >>>
KIND: contract
contract_id: ctr-reqalm-product
client_id: raby-family
project_id: reqalm
in_scope_of: A01, A02, A03, A04, A05, A06, A07, A08, A09, A10, A11, A12.1, ARCH-API, ARCH-API-LAYERS, ARCH-API-RBAC.1, ARCH-APPROVAL, ARCH-APPROVAL-LINE, ARCH-APPROVAL-VIEW, ARCH-APPROVER-SLOTS, ARCH-ATTACH, ARCH-ATTACH-AUDIT, ARCH-ATTACH-ENCRYPT, AR...
in_scope_of_count: 432
covers_releases: rel-pr11-planning-baseline, rel-pr12-devenv-foundation, rel-r0-sequences, rel-r1-browse-clients-projects, rel-r1-browse-ui-catalogs, rel-r1-browse-ui-cp, rel-r1-browse-ui-relations, rel-r1-browse-ui-releases, rel-r1-browse-ui-reqs, rel-r...
covers_releases_count: 37
<<<
RELATIONS:
- TYPE: Parent
  VALUE: SEC-CONTRACTS-EXPORT
- TYPE: Parent
  VALUE: A01
  ROLE: InScopeOf
- TYPE: Parent
  VALUE: A02
  ROLE: InScopeOf
- TYPE: Parent
  VALUE: A03
  ROLE: InScopeOf
- TYPE: Parent
  VALUE: A04
  ROLE: InScopeOf
- TYPE: Parent
  VALUE: A05
  ROLE: InScopeOf
- TYPE: Parent
  VALUE: A06
  ROLE: InScopeOf
- TYPE: Parent
  VALUE: A07
  ROLE: InScopeOf
- TYPE: Parent
  VALUE: A08
  ROLE: InScopeOf
- TYPE: Parent
  VALUE: A09
  ROLE: InScopeOf
- TYPE: Parent
  VALUE: A10
  ROLE: InScopeOf
- TYPE: Parent
  VALUE: A11
  ROLE: InScopeOf
- TYPE: Parent
  VALUE: A12.1
  ROLE: InScopeOf
- TYPE: Parent
  VALUE: ARCH-API
  ROLE: InScopeOf
- TYPE: Parent
  VALUE: ARCH-API-LAYERS
  ROLE: InScopeOf
- TYPE: Parent
  VALUE: ARCH-API-RBAC.1
  ROLE: InScopeOf
- TYPE: Parent
  VALUE: ARCH-APPROVAL
  ROLE: InScopeOf
- TYPE: Parent
  VALUE: ARCH-APPROVAL-LINE
  ROLE: InScopeOf
- TYPE: Parent
  VALUE: ARCH-APPROVAL-VIEW
  ROLE: InScopeOf
- TYPE: Parent
  VALUE: ARCH-APPROVER-SLOTS
  ROLE: InScopeOf
- TYPE: Parent
  VALUE: ARCH-ATTACH
  ROLE: InScopeOf
- TYPE: Parent
  VALUE: ARCH-ATTACH-AUDIT
  ROLE: InScopeOf
- TYPE: Parent
  VALUE: ARCH-ATTACH-ENCRYPT
  ROLE: InScopeOf
- TYPE: Parent
  VALUE: ARCH-ATTACH-PIN-VERSION
  ROLE: InScopeOf
- TYPE: Parent
  VALUE: ARCH-ATTACH-SCAN
  ROLE: InScopeOf
- TYPE: Parent
  VALUE: ARCH-ATTACH-SCOPE
  ROLE: InScopeOf
- TYPE: Parent
  VALUE: ARCH-ATTACH-SERVE
  ROLE: InScopeOf
- TYPE: Parent
  VALUE: ARCH-ATTACH-UPLOAD
  ROLE: InScopeOf
- TYPE: Parent
  VALUE: ARCH-ATTACH-VERSIONS
  ROLE: InScopeOf
- TYPE: Parent
  VALUE: ARCH-AUTH-AGENT-ATTRIBUTION
  ROLE: InScopeOf
- TYPE: Parent
  VALUE: ARCH-AUTH-AS
  ROLE: InScopeOf
- TYPE: Parent
  VALUE: ARCH-AUTH-AUDIENCE
  ROLE: InScopeOf
- TYPE: Parent
  VALUE: ARCH-AUTH-CLAIM-MAP
  ROLE: InScopeOf
- TYPE: Parent
  VALUE: ARCH-AUTH-CLIENTREG
  ROLE: InScopeOf
- TYPE: Parent
  VALUE: ARCH-AUTH-FEDERATION
  ROLE: InScopeOf
- TYPE: Parent
  VALUE: ARCH-AUTH-LOCAL-BREAKGLASS
  ROLE: InScopeOf
- TYPE: Parent
  VALUE: ARCH-AUTH-LOCAL.1
  ROLE: InScopeOf
- TYPE: Parent
  VALUE: ARCH-AUTH-MCP-REQUIRED
  ROLE: InScopeOf
- TYPE: Parent
  VALUE: ARCH-AUTH-METADATA
  ROLE: InScopeOf
- TYPE: Parent
  VALUE: ARCH-AUTH-PKCE
  ROLE: InScopeOf
- TYPE: Parent
  VALUE: ARCH-AUTH-PROFILE
  ROLE: InScopeOf
- TYPE: Parent
  VALUE: ARCH-AUTH-REFRESH
  ROLE: InScopeOf
- TYPE: Parent
  VALUE: ARCH-AUTH-REVOKE
  ROLE: InScopeOf
- TYPE: Parent
  VALUE: ARCH-AUTH-UPSTREAM-CONNECTOR
  ROLE: InScopeOf
- TYPE: Parent
  VALUE: ARCH-AUTH-UPSTREAM-REVOKE
  ROLE: InScopeOf
- TYPE: Parent
  VALUE: ARCH-BACKLOG
  ROLE: InScopeOf
- TYPE: Parent
  VALUE: ARCH-BROWSE-ROADMAP
  ROLE: InScopeOf
- TYPE: Parent
  VALUE: ARCH-BUILD-FOUNDATION
  ROLE: InScopeOf
- TYPE: Parent
  VALUE: ARCH-CAP-APPROVE
  ROLE: InScopeOf
- TYPE: Parent
  VALUE: ARCH-CAP-LINK
  ROLE: InScopeOf
- TYPE: Parent
  VALUE: ARCH-CAT-DRIFT
  ROLE: InScopeOf
- TYPE: Parent
  VALUE: ARCH-CAT-EXTERNAL
  ROLE: InScopeOf
- TYPE: Parent
  VALUE: ARCH-CAT-FREEZE
  ROLE: InScopeOf
- TYPE: Parent
  VALUE: ARCH-CAT-IMPORT
  ROLE: InScopeOf
- TYPE: Parent
  VALUE: ARCH-CAT-IMPRINT
  ROLE: InScopeOf
- TYPE: Parent
  VALUE: ARCH-CAT-MIGRATE
  ROLE: InScopeOf
- TYPE: Parent
  VALUE: ARCH-CAT-PIN
  ROLE: InScopeOf
- TYPE: Parent
  VALUE: ARCH-CAT-PROJECT-ROLLUP
  ROLE: InScopeOf
- TYPE: Parent
  VALUE: ARCH-CAT-REACT
  ROLE: InScopeOf
- TYPE: Parent
  VALUE: ARCH-CAT-SCOPE
  ROLE: InScopeOf
- TYPE: Parent
  VALUE: ARCH-CAT-VISIBILITY
  ROLE: InScopeOf
- TYPE: Parent
  VALUE: ARCH-CHANGESET
  ROLE: InScopeOf
- TYPE: Parent
  VALUE: ARCH-CHANGESET-CONFLICT
  ROLE: InScopeOf
- TYPE: Parent
  VALUE: ARCH-CHANGESET-RBAC
  ROLE: InScopeOf
- TYPE: Parent
  VALUE: ARCH-CHANGESET-RETAIN
  ROLE: InScopeOf
- TYPE: Parent
  VALUE: ARCH-CONTRACT-DOC
  ROLE: InScopeOf
- TYPE: Parent
  VALUE: ARCH-CONTRACT.1
  ROLE: InScopeOf
- TYPE: Parent
  VALUE: ARCH-CP-HIER
  ROLE: InScopeOf
- TYPE: Parent
  VALUE: ARCH-CP-SCOPE
  ROLE: InScopeOf
- TYPE: Parent
  VALUE: ARCH-CRED
  ROLE: InScopeOf
- TYPE: Parent
  VALUE: ARCH-CRED-AUDIT
  ROLE: InScopeOf
- TYPE: Parent
  VALUE: ARCH-CRED-HASH
  ROLE: InScopeOf
- TYPE: Parent
  VALUE: ARCH-CRED-LOCKOUT
  ROLE: InScopeOf
- TYPE: Parent
  VALUE: ARCH-CRED-MFA
  ROLE: InScopeOf
- TYPE: Parent
  VALUE: ARCH-CRED-POLICY
  ROLE: InScopeOf
- TYPE: Parent
  VALUE: ARCH-CRED-REAUTH
  ROLE: InScopeOf
- TYPE: Parent
  VALUE: ARCH-CRED-SESSION
  ROLE: InScopeOf
- TYPE: Parent
  VALUE: ARCH-CRED-TOKENS
  ROLE: InScopeOf
- TYPE: Parent
  VALUE: ARCH-CYBER-GATE
  ROLE: InScopeOf
- TYPE: Parent
  VALUE: ARCH-DEPLOY-MINIMAL
  ROLE: InScopeOf
- TYPE: Parent
  VALUE: ARCH-DEPLOY-PERIPHERALS
  ROLE: InScopeOf
- TYPE: Parent
  VALUE: ARCH-DEVENV-CLONE
  ROLE: InScopeOf
- TYPE: Parent
  VALUE: ARCH-DEVENV-COMPOSE.1
  ROLE: InScopeOf
- TYPE: Parent
  VALUE: ARCH-DEVENV-HEALTH
  ROLE: InScopeOf
- TYPE: Parent
  VALUE: ARCH-DEVENV-IDENTITY.1
  ROLE: InScopeOf
- TYPE: Parent
  VALUE: ARCH-DEVENV-KEYS
  ROLE: InScopeOf
- TYPE: Parent
  VALUE: ARCH-DEVENV-MODES.1
  ROLE: InScopeOf
- TYPE: Parent
  VALUE: ARCH-DEVENV-PARITY.1
  ROLE: InScopeOf
- TYPE: Parent
  VALUE: ARCH-DEVENV-SECRETS
  ROLE: InScopeOf
- TYPE: Parent
  VALUE: ARCH-DEVENV-SEED
  ROLE: InScopeOf
- TYPE: Parent
  VALUE: ARCH-FIGMA
  ROLE: InScopeOf
- TYPE: Parent
  VALUE: ARCH-FIGMA-AUTH
  ROLE: InScopeOf
- TYPE: Parent
  VALUE: ARCH-FIGMA-EGRESS
  ROLE: InScopeOf
- TYPE: Parent
  VALUE: ARCH-GANTT
  ROLE: InScopeOf
- TYPE: Parent
  VALUE: ARCH-GATE-MODEL
  ROLE: InScopeOf
- TYPE: Parent
  VALUE: ARCH-GATE-SIGNOFF
  ROLE: InScopeOf
- TYPE: Parent
  VALUE: ARCH-HIER-CAP-PARTOF
  ROLE: InScopeOf
- TYPE: Parent
  VALUE: ARCH-HIER-REQ-DECOMP
  ROLE: InScopeOf
- TYPE: Parent
  VALUE: ARCH-HIER-SECTION-GROUP
  ROLE: InScopeOf
- TYPE: Parent
  VALUE: ARCH-HIER-USES-DEP
  ROLE: InScopeOf
- TYPE: Parent
  VALUE: ARCH-HOOK-EVAL
  ROLE: InScopeOf
- TYPE: Parent
  VALUE: ARCH-KEY
  ROLE: InScopeOf
- TYPE: Parent
  VALUE: ARCH-KEY-BREAKGLASS
  ROLE: InScopeOf
- TYPE: Parent
  VALUE: ARCH-KEY-CUSTODIAN
  ROLE: InScopeOf
- TYPE: Parent
  VALUE: ARCH-KEY-FAILCLOSED
  ROLE: InScopeOf
- TYPE: Parent
  VALUE: ARCH-KEY-FIPS
  ROLE: InScopeOf
- TYPE: Parent
  VALUE: ARCH-KEY-JWKS
  ROLE: InScopeOf
- TYPE: Parent
  VALUE: ARCH-KEY-LIFECYCLE
  ROLE: InScopeOf
- TYPE: Parent
  VALUE: ARCH-KEY-PROVIDER
  ROLE: InScopeOf
- TYPE: Parent
  VALUE: ARCH-KEY-RUNTIME-CACHE
  ROLE: InScopeOf
- TYPE: Parent
  VALUE: ARCH-KEY-SCOPE
  ROLE: InScopeOf
- TYPE: Parent
  VALUE: ARCH-LOCKED
  ROLE: InScopeOf
- TYPE: Parent
  VALUE: ARCH-MINT-KIND
  ROLE: InScopeOf
- TYPE: Parent
  VALUE: ARCH-OTEL
  ROLE: InScopeOf
- TYPE: Parent
  VALUE: ARCH-OTEL-TRACE
  ROLE: InScopeOf
- TYPE: Parent
  VALUE: ARCH-PLANNING-GATES
  ROLE: InScopeOf
- TYPE: Parent
  VALUE: ARCH-RELEASE
  ROLE: InScopeOf
- TYPE: Parent
  VALUE: ARCH-RELEASE-FREEZE
  ROLE: InScopeOf
- TYPE: Parent
  VALUE: ARCH-REQ-AC-FACET
  ROLE: InScopeOf
- TYPE: Parent
  VALUE: ARCH-REQ-AC-ROLLUP
  ROLE: InScopeOf
- TYPE: Parent
  VALUE: ARCH-REQ-VS-CAP
  ROLE: InScopeOf
- TYPE: Parent
  VALUE: ARCH-SEC-CAT-FK
  ROLE: InScopeOf
- TYPE: Parent
  VALUE: ARCH-SEC-CAT-LABEL-IMPRINT
  ROLE: InScopeOf
- TYPE: Parent
  VALUE: ARCH-SEC-EDGE-DEDUPE-API
  ROLE: InScopeOf
- TYPE: Parent
  VALUE: ARCH-SEC-EDGE-DEDUPE-DB
  ROLE: InScopeOf
- TYPE: Parent
  VALUE: ARCH-SEC-HEADERS
  ROLE: InScopeOf
- TYPE: Parent
  VALUE: ARCH-SEC-LOADER-EDGE-SYNC
  ROLE: InScopeOf
- TYPE: Parent
  VALUE: ARCH-SEC-REL-PAGING
  ROLE: InScopeOf
- TYPE: Parent
  VALUE: ARCH-SEC-REL-STUB
  ROLE: InScopeOf
- TYPE: Parent
  VALUE: ARCH-SEC-SEED-INTEGRITY
  ROLE: InScopeOf
- TYPE: Parent
  VALUE: ARCH-SEC-XPROJ-READ
  ROLE: InScopeOf
- TYPE: Parent
  VALUE: ARCH-SUBJECT-KIND
  ROLE: InScopeOf
- TYPE: Parent
  VALUE: ARCH-SUCCESSION-HASH
  ROLE: InScopeOf
- TYPE: Parent
  VALUE: ARCH-SUSPECT-QUEUE
  ROLE: InScopeOf
- TYPE: Parent
  VALUE: ARCH-SUSPECT.1
  ROLE: InScopeOf
- TYPE: Parent
  VALUE: ARCH-TEST-HARNESS-TEARDOWN
  ROLE: InScopeOf
- TYPE: Parent
  VALUE: ARCH-TRACE-INHERIT-HYBRID
  ROLE: InScopeOf
- TYPE: Parent
  VALUE: ARCH-TRACE-INHERIT-USES
  ROLE: InScopeOf
- TYPE: Parent
  VALUE: ARCH-TRACE-LAYOUT-WORKER
  ROLE: InScopeOf
- TYPE: Parent
  VALUE: ARCH-TRACE-RECHECK
  ROLE: InScopeOf
- TYPE: Parent
  VALUE: ARCH-TRACE-VIEW-CCM
  ROLE: InScopeOf
- TYPE: Parent
  VALUE: ARCH-TRACE-VIEW-RTM
  ROLE: InScopeOf
- TYPE: Parent
  VALUE: ARCH-UI
  ROLE: InScopeOf
- TYPE: Parent
  VALUE: ARCH-UI-GUARD
  ROLE: InScopeOf
- TYPE: Parent
  VALUE: ARCH-UI-KIT-SHARED
  ROLE: InScopeOf
- TYPE: Parent
  VALUE: ARCH-VER
  ROLE: InScopeOf
- TYPE: Parent
  VALUE: ARCH-VER-SUCC
  ROLE: InScopeOf
- TYPE: Parent
  VALUE: ARCH-VER-TOMB
  ROLE: InScopeOf
- TYPE: Parent
  VALUE: ARCH-VERIFICATION
  ROLE: InScopeOf
- TYPE: Parent
  VALUE: ARCH-VERIFICATION-GATE
  ROLE: InScopeOf
- TYPE: Parent
  VALUE: ARCH-WF-ADMIN
  ROLE: InScopeOf
- TYPE: Parent
  VALUE: ARCH-WORKFLOW
  ROLE: InScopeOf
- TYPE: Parent
  VALUE: ARCH-WRITE-AUDIT-FLOOD
  ROLE: InScopeOf
- TYPE: Parent
  VALUE: ARCH-WRITE-REPOSITORY-LAYER
  ROLE: InScopeOf
- TYPE: Parent
  VALUE: ARCH-WRITE-RESERVED-IDS
  ROLE: InScopeOf
- TYPE: Parent
  VALUE: ARCH-WRITE-TRUNCATE-GUARD
  ROLE: InScopeOf
- TYPE: Parent
  VALUE: ARCH-WRITE-UOW-AUDIT
  ROLE: InScopeOf
- TYPE: Parent
  VALUE: ARCH-WRITE-VERSION-UNIQUE
  ROLE: InScopeOf
- TYPE: Parent
  VALUE: B01
  ROLE: InScopeOf
- TYPE: Parent
  VALUE: B02
  ROLE: InScopeOf
- TYPE: Parent
  VALUE: B03
  ROLE: InScopeOf
- TYPE: Parent
  VALUE: B04
  ROLE: InScopeOf
- TYPE: Parent
  VALUE: B05
  ROLE: InScopeOf
- TYPE: Parent
  VALUE: B06
  ROLE: InScopeOf
- TYPE: Parent
  VALUE: B07
  ROLE: InScopeOf
- TYPE: Parent
  VALUE: B08
  ROLE: InScopeOf
- TYPE: Parent
  VALUE: C01
  ROLE: InScopeOf
- TYPE: Parent
  VALUE: C02
  ROLE: InScopeOf
- TYPE: Parent
  VALUE: C03
  ROLE: InScopeOf
- TYPE: Parent
  VALUE: C04
  ROLE: InScopeOf
- TYPE: Parent
  VALUE: C05
  ROLE: InScopeOf
- TYPE: Parent
  VALUE: C06
  ROLE: InScopeOf
- TYPE: Parent
  VALUE: C07
  ROLE: InScopeOf
- TYPE: Parent
  VALUE: C08
  ROLE: InScopeOf
- TYPE: Parent
  VALUE: CAP-AGENT-ACCESS
  ROLE: InScopeOf
- TYPE: Parent
  VALUE: CAP-API-DOCS-SEED-SUMMARY
  ROLE: InScopeOf
- TYPE: Parent
  VALUE: CAP-ATTACH-READ
  ROLE: InScopeOf
- TYPE: Parent
  VALUE: CAP-ATTACH-WRITE
  ROLE: InScopeOf
- TYPE: Parent
  VALUE: CAP-AUDIT
  ROLE: InScopeOf
- TYPE: Parent
  VALUE: CAP-AUTH-AUDIT
  ROLE: InScopeOf
- TYPE: Parent
  VALUE: CAP-AUTH-HARDEN.1
  ROLE: InScopeOf
- TYPE: Parent
  VALUE: CAP-AUTH-UPSTREAM-SEAM
  ROLE: InScopeOf
- TYPE: Parent
  VALUE: CAP-BROWSE-CP
  ROLE: InScopeOf
- TYPE: Parent
  VALUE: CAP-BROWSE-ROADMAP
  ROLE: InScopeOf
- TYPE: Parent
  VALUE: CAP-BROWSE-UI-CATALOGS
  ROLE: InScopeOf
- TYPE: Parent
  VALUE: CAP-BROWSE-UI-CP.1
  ROLE: InScopeOf
- TYPE: Parent
  VALUE: CAP-BROWSE-UI-RELATIONS.1
  ROLE: InScopeOf
- TYPE: Parent
  VALUE: CAP-BROWSE-UI-RELEASES.1
  ROLE: InScopeOf
- TYPE: Parent
  VALUE: CAP-BROWSE-UI-REQS.1
  ROLE: InScopeOf
- TYPE: Parent
  VALUE: CAP-BROWSE-UI-TREE.1
  ROLE: InScopeOf
- TYPE: Parent
  VALUE: CAP-CATALOGS-API
  ROLE: InScopeOf
- TYPE: Parent
  VALUE: CAP-CONTRACT-UI
  ROLE: InScopeOf
- TYPE: Parent
  VALUE: CAP-CONTRACTS-LOADER
  ROLE: InScopeOf
- TYPE: Parent
  VALUE: CAP-CRED-STORE
  ROLE: InScopeOf
- TYPE: Parent
  VALUE: CAP-CRITERIA-RELEASE-REVIEW
  ROLE: InScopeOf
- TYPE: Parent
  VALUE: CAP-DEVENV-COMPOSE
  ROLE: InScopeOf
- TYPE: Parent
  VALUE: CAP-DEVENV-DOCKERFILE-ROLES
  ROLE: InScopeOf
- TYPE: Parent
  VALUE: CAP-DEVENV-INIT
  ROLE: InScopeOf
- TYPE: Parent
  VALUE: CAP-DEVENV-LF-ENDINGS
  ROLE: InScopeOf
- TYPE: Parent
  VALUE: CAP-DEVENV-MIGRATE-SEED
  ROLE: InScopeOf
- TYPE: Parent
  VALUE: CAP-DEVENV-MONOREPO
  ROLE: InScopeOf
- TYPE: Parent
  VALUE: CAP-DEVENV-OPENBAO-BOOTSTRAP
  ROLE: InScopeOf
- TYPE: Parent
  VALUE: CAP-DEVENV-PERIPHERALS
  ROLE: InScopeOf
- TYPE: Parent
  VALUE: CAP-DEVENV-SEED-RESET
  ROLE: InScopeOf
- TYPE: Parent
  VALUE: CAP-DEVENV-SMOKE
  ROLE: InScopeOf
- TYPE: Parent
  VALUE: CAP-DEVENV-SMOKE-COMPOSE-ISOLATION
  ROLE: InScopeOf
- TYPE: Parent
  VALUE: CAP-DEVENV-STARTUP-BACKOFF
  ROLE: InScopeOf
- TYPE: Parent
  VALUE: CAP-HEALTH-LIVENESS
  ROLE: InScopeOf
- TYPE: Parent
  VALUE: CAP-KEY-ENVELOPE
  ROLE: InScopeOf
- TYPE: Parent
  VALUE: CAP-MCP-DESK
  ROLE: InScopeOf
- TYPE: Parent
  VALUE: CAP-MFA-ENROLL
  ROLE: InScopeOf
- TYPE: Parent
  VALUE: CAP-MFA-QR
  ROLE: InScopeOf
- TYPE: Parent
  VALUE: CAP-OAUTH-AS
  ROLE: InScopeOf
- TYPE: Parent
  VALUE: CAP-OTEL-AUDIT-TRACE
  ROLE: InScopeOf
- TYPE: Parent
  VALUE: CAP-OTEL-EXPORT
  ROLE: InScopeOf
- TYPE: Parent
  VALUE: CAP-OTEL-KEY-DEP
  ROLE: InScopeOf
- TYPE: Parent
  VALUE: CAP-OTEL-OPERATION-SPANS
  ROLE: InScopeOf
- TYPE: Parent
  VALUE: CAP-OTEL-SDK-BOOTSTRAP
  ROLE: InScopeOf
- TYPE: Parent
  VALUE: CAP-OTEL-SPAN-SAFE-ERRORS
  ROLE: InScopeOf
- TYPE: Parent
  VALUE: CAP-OTEL-TEST-HARNESS
  ROLE: InScopeOf
- TYPE: Parent
  VALUE: CAP-OTEL-W3C-CONTEXT
  ROLE: InScopeOf
- TYPE: Parent
  VALUE: CAP-PROD-SELFCHECK
  ROLE: InScopeOf
- TYPE: Parent
  VALUE: CAP-RBAC.1
  ROLE: InScopeOf
- TYPE: Parent
  VALUE: CAP-READ-CONTRACTS
  ROLE: InScopeOf
- TYPE: Parent
  VALUE: CAP-READ-HIERARCHY
  ROLE: InScopeOf
- TYPE: Parent
  VALUE: CAP-READ-RELEASES
  ROLE: InScopeOf
- TYPE: Parent
  VALUE: CAP-READ-REQS
  ROLE: InScopeOf
- TYPE: Parent
  VALUE: CAP-READY-PROBES
  ROLE: InScopeOf
- TYPE: Parent
  VALUE: CAP-RELATIONS-API
  ROLE: InScopeOf
- TYPE: Parent
  VALUE: CAP-RENAME-REQALM
  ROLE: InScopeOf
- TYPE: Parent
  VALUE: CAP-REQALM-CONTRACTS
  ROLE: InScopeOf
- TYPE: Parent
  VALUE: CAP-SCOPED-VIEW.1
  ROLE: InScopeOf
- TYPE: Parent
  VALUE: CAP-SEED-ATTACH-FIGMA
  ROLE: InScopeOf
- TYPE: Parent
  VALUE: CAP-SEED-GROOMING
  ROLE: InScopeOf
- TYPE: Parent
  VALUE: CAP-SSO.1
  ROLE: InScopeOf
- TYPE: Parent
  VALUE: CAP-SVC-AUDIT-APPEND
  ROLE: InScopeOf
- TYPE: Parent
  VALUE: CAP-SVC-BUSINESS-ROUTE-AUDIT
  ROLE: InScopeOf
- TYPE: Parent
  VALUE: CAP-SVC-IMPLICIT-PUBLIC-EXACT
  ROLE: InScopeOf
- TYPE: Parent
  VALUE: CAP-SVC-MODULE-BOOTSTRAP
  ROLE: InScopeOf
- TYPE: Parent
  VALUE: CAP-SVC-NON-API-AUTH-AUDIT
  ROLE: InScopeOf
- TYPE: Parent
  VALUE: CAP-SVC-OPERATION-EXECUTOR.1
  ROLE: InScopeOf
- TYPE: Parent
  VALUE: CAP-SVC-OPERATION-ROUTE
  ROLE: InScopeOf
- TYPE: Parent
  VALUE: CAP-SVC-PROBLEM-JSON
  ROLE: InScopeOf
- TYPE: Parent
  VALUE: CAP-SVC-PROJECT-ID-SLUG
  ROLE: InScopeOf
- TYPE: Parent
  VALUE: CAP-SVC-PROJECT-READ
  ROLE: InScopeOf
- TYPE: Parent
  VALUE: CAP-SVC-REQUEST-CONTEXT
  ROLE: InScopeOf
- TYPE: Parent
  VALUE: CAP-SVC-RESULT-ENVELOPE
  ROLE: InScopeOf
- TYPE: Parent
  VALUE: CAP-SVC-ROUTE-REGISTRY
  ROLE: InScopeOf
- TYPE: Parent
  VALUE: CAP-SVC-STATIC-DEP-PATCH
  ROLE: InScopeOf
- TYPE: Parent
  VALUE: CAP-SVC-STRUCTURED-LOG
  ROLE: InScopeOf
- TYPE: Parent
  VALUE: CAP-TEST-AUTH-HYGIENE
  ROLE: InScopeOf
- TYPE: Parent
  VALUE: CAP-TEST-AUTH-ROUTES
  ROLE: InScopeOf
- TYPE: Parent
  VALUE: CAP-TEST-MEMORY-KEYPROVIDER
  ROLE: InScopeOf
- TYPE: Parent
  VALUE: CAP-TEST-PGLITE-DB
  ROLE: InScopeOf
- TYPE: Parent
  VALUE: CAP-TEST-PNPM-GATE
  ROLE: InScopeOf
- TYPE: Parent
  VALUE: CAP-TEST-PROD-BUILD-EXCLUDE
  ROLE: InScopeOf
- TYPE: Parent
  VALUE: CAP-TRACE-INHERIT-USES
  ROLE: InScopeOf
- TYPE: Parent
  VALUE: CAP-TREE
  ROLE: InScopeOf
- TYPE: Parent
  VALUE: CAP-UI-FRAME.2
  ROLE: InScopeOf
- TYPE: Parent
  VALUE: CAP-UI-HEADER-NAV.1
  ROLE: InScopeOf
- TYPE: Parent
  VALUE: CAP-UI-KIT
  ROLE: InScopeOf
- TYPE: Parent
  VALUE: CAP-UI-KIT-CHROME
  ROLE: InScopeOf
- TYPE: Parent
  VALUE: CAP-UI-KIT-TREE
  ROLE: InScopeOf
- TYPE: Parent
  VALUE: CAP-UI-LAYOUT
  ROLE: InScopeOf
- TYPE: Parent
  VALUE: CAP-UI-VIEW-CAP-DETAIL
  ROLE: InScopeOf
- TYPE: Parent
  VALUE: CAP-UI-VIEW-CAP-FOCUS
  ROLE: InScopeOf
- TYPE: Parent
  VALUE: CAP-UI-VIEW-CATALOG
  ROLE: InScopeOf
- TYPE: Parent
  VALUE: CAP-UI-VIEW-CCM
  ROLE: InScopeOf
- TYPE: Parent
  VALUE: CAP-UI-VIEW-CRITERIA
  ROLE: InScopeOf
- TYPE: Parent
  VALUE: CAP-UI-VIEW-RTM
  ROLE: InScopeOf
- TYPE: Parent
  VALUE: CAP-VERSION-UI
  ROLE: InScopeOf
- TYPE: Parent
  VALUE: D01
  ROLE: InScopeOf
- TYPE: Parent
  VALUE: D02
  ROLE: InScopeOf
- TYPE: Parent
  VALUE: D03
  ROLE: InScopeOf
- TYPE: Parent
  VALUE: D04
  ROLE: InScopeOf
- TYPE: Parent
  VALUE: D05
  ROLE: InScopeOf
- TYPE: Parent
  VALUE: D06
  ROLE: InScopeOf
- TYPE: Parent
  VALUE: D07
  ROLE: InScopeOf
- TYPE: Parent
  VALUE: D08
  ROLE: InScopeOf
- TYPE: Parent
  VALUE: D09
  ROLE: InScopeOf
- TYPE: Parent
  VALUE: D10
  ROLE: InScopeOf
- TYPE: Parent
  VALUE: D11
  ROLE: InScopeOf
- TYPE: Parent
  VALUE: D12
  ROLE: InScopeOf
- TYPE: Parent
  VALUE: D13
  ROLE: InScopeOf
- TYPE: Parent
  VALUE: E01
  ROLE: InScopeOf
- TYPE: Parent
  VALUE: E02
  ROLE: InScopeOf
- TYPE: Parent
  VALUE: E03
  ROLE: InScopeOf
- TYPE: Parent
  VALUE: E04
  ROLE: InScopeOf
- TYPE: Parent
  VALUE: E05
  ROLE: InScopeOf
- TYPE: Parent
  VALUE: E06
  ROLE: InScopeOf
- TYPE: Parent
  VALUE: E07
  ROLE: InScopeOf
- TYPE: Parent
  VALUE: F01
  ROLE: InScopeOf
- TYPE: Parent
  VALUE: F02
  ROLE: InScopeOf
- TYPE: Parent
  VALUE: F03
  ROLE: InScopeOf
- TYPE: Parent
  VALUE: F04
  ROLE: InScopeOf
- TYPE: Parent
  VALUE: F05
  ROLE: InScopeOf
- TYPE: Parent
  VALUE: F06
  ROLE: InScopeOf
- TYPE: Parent
  VALUE: F07
  ROLE: InScopeOf
- TYPE: Parent
  VALUE: F08
  ROLE: InScopeOf
- TYPE: Parent
  VALUE: F09
  ROLE: InScopeOf
- TYPE: Parent
  VALUE: F10
  ROLE: InScopeOf
- TYPE: Parent
  VALUE: FIX-ALLOW-AGENT-ATTRIBUTION
  ROLE: InScopeOf
- TYPE: Parent
  VALUE: FIX-ALLOW-APP-ROLE-SPLIT
  ROLE: InScopeOf
- TYPE: Parent
  VALUE: FIX-ALLOW-APPROVE-LINE
  ROLE: InScopeOf
- TYPE: Parent
  VALUE: FIX-ALLOW-AUDIT-CLIENT
  ROLE: InScopeOf
- TYPE: Parent
  VALUE: FIX-ALLOW-BREAKGLASS-LOCAL-ADMIN
  ROLE: InScopeOf
- TYPE: Parent
  VALUE: FIX-ALLOW-CLIENT-CREATE
  ROLE: InScopeOf
- TYPE: Parent
  VALUE: FIX-ALLOW-CRED-HASH-ONLY
  ROLE: InScopeOf
- TYPE: Parent
  VALUE: FIX-ALLOW-DEVENV-MIN-CONTAINERS
  ROLE: InScopeOf
- TYPE: Parent
  VALUE: FIX-ALLOW-DEVENV-SEED-IDEMPOTENT
  ROLE: InScopeOf
- TYPE: Parent
  VALUE: FIX-ALLOW-DEVENV-SMOKE
  ROLE: InScopeOf
- TYPE: Parent
  VALUE: FIX-ALLOW-FEDERATED-SSO-VIA-AS
  ROLE: InScopeOf
- TYPE: Parent
  VALUE: FIX-ALLOW-KEK-REWRAP-ONLINE
  ROLE: InScopeOf
- TYPE: Parent
  VALUE: FIX-ALLOW-MCP-OAUTH-FEDERATED-ONLY
  ROLE: InScopeOf
- TYPE: Parent
  VALUE: FIX-ALLOW-MCP-OAUTH-PKCE
  ROLE: InScopeOf
- TYPE: Parent
  VALUE: FIX-ALLOW-PIN-MIGRATE-MINT
  ROLE: InScopeOf
- TYPE: Parent
  VALUE: FIX-ALLOW-PIN-REQUEST
  ROLE: InScopeOf
- TYPE: Parent
  VALUE: FIX-ALLOW-SECURITY-PIN-APPLY
  ROLE: InScopeOf
- TYPE: Parent
  VALUE: FIX-ALLOW-STATUS-SUPERSEDE
  ROLE: InScopeOf
- TYPE: Parent
  VALUE: FIX-ALLOW-STEWARD-UPDATE
  ROLE: InScopeOf
- TYPE: Parent
  VALUE: FIX-ALLOW-SUCCEED
  ROLE: InScopeOf
- TYPE: Parent
  VALUE: FIX-ALLOW-SUSPECT-CARRY
  ROLE: InScopeOf
- TYPE: Parent
  VALUE: FIX-ALLOW-SUSPECT-DROP
  ROLE: InScopeOf
- TYPE: Parent
  VALUE: FIX-ALLOW-SUSPECT-KEEP-PINNED
  ROLE: InScopeOf
- TYPE: Parent
  VALUE: FIX-COMPARE-2HOP
  ROLE: InScopeOf
- TYPE: Parent
  VALUE: FIX-CONTRACT-DOC-CTX
  ROLE: InScopeOf
- TYPE: Parent
  VALUE: FIX-CONTRACT-DOC-NOCTX
  ROLE: InScopeOf
- TYPE: Parent
  VALUE: FIX-DENY-APPROVE-WITHOUT-SLOT
  ROLE: InScopeOf
- TYPE: Parent
  VALUE: FIX-DENY-AUDIT-CROSS-CLIENT
  ROLE: InScopeOf
- TYPE: Parent
  VALUE: FIX-DENY-AUTHOR-PIN-APPLY
  ROLE: InScopeOf
- TYPE: Parent
  VALUE: FIX-DENY-CLOSED-LINK
  ROLE: InScopeOf
- TYPE: Parent
  VALUE: FIX-DENY-CROSS-CLIENT
  ROLE: InScopeOf
- TYPE: Parent
  VALUE: FIX-DENY-CROSS-TENANT-CONNECTOR
  ROLE: InScopeOf
- TYPE: Parent
  VALUE: FIX-DENY-DCR-DISABLED
  ROLE: InScopeOf
- TYPE: Parent
  VALUE: FIX-DENY-DEV-KEK-IN-PROD
  ROLE: InScopeOf
- TYPE: Parent
  VALUE: FIX-DENY-DEVENV-PROD-LOGIN.1
  ROLE: InScopeOf
- TYPE: Parent
  VALUE: FIX-DENY-EDIT-ACTIVE
  ROLE: InScopeOf
- TYPE: Parent
  VALUE: FIX-DENY-KEK-UNREACHABLE-PROD
  ROLE: InScopeOf
- TYPE: Parent
  VALUE: FIX-DENY-KEYOP-NO-CUSTODIAN
  ROLE: InScopeOf
- TYPE: Parent
  VALUE: FIX-DENY-LOCAL-LOGIN-PROFILE-OFF
  ROLE: InScopeOf
- TYPE: Parent
  VALUE: FIX-DENY-LOCKOUT
  ROLE: InScopeOf
- TYPE: Parent
  VALUE: FIX-DENY-MCP-ESCALATE
  ROLE: InScopeOf
- TYPE: Parent
  VALUE: FIX-DENY-MCP-WRONG-AUDIENCE
  ROLE: InScopeOf
- TYPE: Parent
  VALUE: FIX-DENY-NO-GRANT
  ROLE: InScopeOf
- TYPE: Parent
  VALUE: FIX-DENY-NOOP-CONTENT
  ROLE: InScopeOf
- TYPE: Parent
  VALUE: FIX-DENY-NOOP-SUCCESSOR
  ROLE: InScopeOf
- TYPE: Parent
  VALUE: FIX-DENY-PKCE-PLAIN
  ROLE: InScopeOf
- TYPE: Parent
  VALUE: FIX-DENY-PRIORITY-UNAPPROVED
  ROLE: InScopeOf
- TYPE: Parent
  VALUE: FIX-DENY-PRIV-NO-MFA
  ROLE: InScopeOf
- TYPE: Parent
  VALUE: FIX-DENY-READER-GRANT
  ROLE: InScopeOf
- TYPE: Parent
  VALUE: FIX-DENY-REFRESH-REUSE
  ROLE: InScopeOf
- TYPE: Parent
  VALUE: FIX-DENY-REVERT-NON-LATEST
  ROLE: InScopeOf
- TYPE: Parent
  VALUE: FIX-DENY-REVOKED
  ROLE: InScopeOf
- TYPE: Parent
  VALUE: FIX-DENY-REVOKED-TOKEN
  ROLE: InScopeOf
- TYPE: Parent
  VALUE: FIX-DENY-SECOND-ACTIVE
  ROLE: InScopeOf
- TYPE: Parent
  VALUE: FIX-DENY-SESSION-IDLE
  ROLE: InScopeOf
- TYPE: Parent
  VALUE: FIX-DENY-SHIP-UNSIGNED
  ROLE: InScopeOf
- TYPE: Parent
  VALUE: FIX-DENY-SHIP-WITH-OPEN-SUSPECT
  ROLE: InScopeOf
- TYPE: Parent
  VALUE: FIX-DENY-SHIPPED-DELIVERS
  ROLE: InScopeOf
- TYPE: Parent
  VALUE: FIX-DENY-STEPUP-STALE-AUTH
  ROLE: InScopeOf
- TYPE: Parent
  VALUE: FIX-DENY-STEWARD-STANDARD
  ROLE: InScopeOf
- TYPE: Parent
  VALUE: FIX-DENY-UPSTREAM-LOGOUT-PROPAGATED
  ROLE: InScopeOf
- TYPE: Parent
  VALUE: FIX-DENY-UPSTREAM-TOKEN-AT-API
  ROLE: InScopeOf
- TYPE: Parent
  VALUE: FIX-EXPORT-L02-GOLDEN
  ROLE: InScopeOf
- TYPE: Parent
  VALUE: FIX-GRANDFATHER-SEED-APPROVED
  ROLE: InScopeOf
- TYPE: Parent
  VALUE: FIX-JWKS-ROTATION-OVERLAP
  ROLE: InScopeOf
- TYPE: Parent
  VALUE: FIX-PLANNING-BLOCKED-AFTER-CONTENT-N
  ROLE: InScopeOf
- TYPE: Parent
  VALUE: FIX-REL-SNAP
  ROLE: InScopeOf
- TYPE: Parent
  VALUE: FIX-SAMPLE-APPROVED
  ROLE: InScopeOf
- TYPE: Parent
  VALUE: FIX-SAMPLE-UNAPPROVED
  ROLE: InScopeOf
- TYPE: Parent
  VALUE: FIX-SAMPLE-WF-CAP
  ROLE: InScopeOf
- TYPE: Parent
  VALUE: FIX-SAMPLE-WF-REQ
  ROLE: InScopeOf
- TYPE: Parent
  VALUE: FIX-SUCC-2HOP.2
  ROLE: InScopeOf
- TYPE: Parent
  VALUE: FIX-SUSPECT-ON-CONTENT-N
  ROLE: InScopeOf
- TYPE: Parent
  VALUE: G01
  ROLE: InScopeOf
- TYPE: Parent
  VALUE: G02
  ROLE: InScopeOf
- TYPE: Parent
  VALUE: G03
  ROLE: InScopeOf
- TYPE: Parent
  VALUE: G04
  ROLE: InScopeOf
- TYPE: Parent
  VALUE: G05
  ROLE: InScopeOf
- TYPE: Parent
  VALUE: G06
  ROLE: InScopeOf
- TYPE: Parent
  VALUE: G07
  ROLE: InScopeOf
- TYPE: Parent
  VALUE: G08
  ROLE: InScopeOf
- TYPE: Parent
  VALUE: H01
  ROLE: InScopeOf
- TYPE: Parent
  VALUE: H02
  ROLE: InScopeOf
- TYPE: Parent
  VALUE: H03
  ROLE: InScopeOf
- TYPE: Parent
  VALUE: H04
  ROLE: InScopeOf
- TYPE: Parent
  VALUE: H05
  ROLE: InScopeOf
- TYPE: Parent
  VALUE: H06
  ROLE: InScopeOf
- TYPE: Parent
  VALUE: H07
  ROLE: InScopeOf
- TYPE: Parent
  VALUE: H08
  ROLE: InScopeOf
- TYPE: Parent
  VALUE: H09
  ROLE: InScopeOf
- TYPE: Parent
  VALUE: H10
  ROLE: InScopeOf
- TYPE: Parent
  VALUE: I01
  ROLE: InScopeOf
- TYPE: Parent
  VALUE: I02
  ROLE: InScopeOf
- TYPE: Parent
  VALUE: I03
  ROLE: InScopeOf
- TYPE: Parent
  VALUE: I04
  ROLE: InScopeOf
- TYPE: Parent
  VALUE: I05
  ROLE: InScopeOf
- TYPE: Parent
  VALUE: I06
  ROLE: InScopeOf
- TYPE: Parent
  VALUE: J01
  ROLE: InScopeOf
- TYPE: Parent
  VALUE: J02
  ROLE: InScopeOf
- TYPE: Parent
  VALUE: J03
  ROLE: InScopeOf
- TYPE: Parent
  VALUE: J04
  ROLE: InScopeOf
- TYPE: Parent
  VALUE: J05
  ROLE: InScopeOf
- TYPE: Parent
  VALUE: J06
  ROLE: InScopeOf
- TYPE: Parent
  VALUE: J07
  ROLE: InScopeOf
- TYPE: Parent
  VALUE: J08
  ROLE: InScopeOf
- TYPE: Parent
  VALUE: K01
  ROLE: InScopeOf
- TYPE: Parent
  VALUE: K02
  ROLE: InScopeOf
- TYPE: Parent
  VALUE: K03
  ROLE: InScopeOf
- TYPE: Parent
  VALUE: K04
  ROLE: InScopeOf
- TYPE: Parent
  VALUE: K05
  ROLE: InScopeOf
- TYPE: Parent
  VALUE: K06
  ROLE: InScopeOf
- TYPE: Parent
  VALUE: L01
  ROLE: InScopeOf
- TYPE: Parent
  VALUE: L02
  ROLE: InScopeOf
- TYPE: Parent
  VALUE: L03
  ROLE: InScopeOf
- TYPE: Parent
  VALUE: L04
  ROLE: InScopeOf
- TYPE: Parent
  VALUE: M01
  ROLE: InScopeOf
- TYPE: Parent
  VALUE: M02
  ROLE: InScopeOf
- TYPE: Parent
  VALUE: M03
  ROLE: InScopeOf
- TYPE: Parent
  VALUE: M04
  ROLE: InScopeOf
- TYPE: Parent
  VALUE: M05
  ROLE: InScopeOf
- TYPE: Parent
  VALUE: M06
  ROLE: InScopeOf
- TYPE: Parent
  VALUE: M07
  ROLE: InScopeOf
- TYPE: Parent
  VALUE: MC01.1
  ROLE: InScopeOf
- TYPE: Parent
  VALUE: MC02
  ROLE: InScopeOf
- TYPE: Parent
  VALUE: MC03
  ROLE: InScopeOf
- TYPE: Parent
  VALUE: N01
  ROLE: InScopeOf
- TYPE: Parent
  VALUE: N02
  ROLE: InScopeOf
- TYPE: Parent
  VALUE: N03
  ROLE: InScopeOf
- TYPE: Parent
  VALUE: SPIKE-FIGMA-FEASIBILITY
  ROLE: InScopeOf
- TYPE: Parent
  VALUE: UI-APPROVE-LINE
  ROLE: InScopeOf
- TYPE: Parent
  VALUE: UI-APPROVE-TREE
  ROLE: InScopeOf
- TYPE: Parent
  VALUE: WANT-CHANGESET-FIELD-UNDO
  ROLE: InScopeOf
- TYPE: Parent
  VALUE: RELEASE-rel-pr11-planning-baseline
  ROLE: CoversRelease
- TYPE: Parent
  VALUE: RELEASE-rel-pr12-devenv-foundation
  ROLE: CoversRelease
- TYPE: Parent
  VALUE: RELEASE-rel-r0-sequences
  ROLE: CoversRelease
- TYPE: Parent
  VALUE: RELEASE-rel-r1-browse-clients-projects
  ROLE: CoversRelease
- TYPE: Parent
  VALUE: RELEASE-rel-r1-browse-ui-catalogs
  ROLE: CoversRelease
- TYPE: Parent
  VALUE: RELEASE-rel-r1-browse-ui-cp
  ROLE: CoversRelease
- TYPE: Parent
  VALUE: RELEASE-rel-r1-browse-ui-relations
  ROLE: CoversRelease
- TYPE: Parent
  VALUE: RELEASE-rel-r1-browse-ui-releases
  ROLE: CoversRelease
- TYPE: Parent
  VALUE: RELEASE-rel-r1-browse-ui-reqs
  ROLE: CoversRelease
- TYPE: Parent
  VALUE: RELEASE-rel-r1-browse-ui-tree
  ROLE: CoversRelease
- TYPE: Parent
  VALUE: RELEASE-rel-r1-catalogs-api
  ROLE: CoversRelease
- TYPE: Parent
  VALUE: RELEASE-rel-r1-contracts-loader
  ROLE: CoversRelease
- TYPE: Parent
  VALUE: RELEASE-rel-r1-core-alm
  ROLE: CoversRelease
- TYPE: Parent
  VALUE: RELEASE-rel-r1-criteria-release-review
  ROLE: CoversRelease
- TYPE: Parent
  VALUE: RELEASE-rel-r1-foundation-shell-auth
  ROLE: CoversRelease
- TYPE: Parent
  VALUE: RELEASE-rel-r1-lf-endings
  ROLE: CoversRelease
- TYPE: Parent
  VALUE: RELEASE-rel-r1-mfa-qr
  ROLE: CoversRelease
- TYPE: Parent
  VALUE: RELEASE-rel-r1-otel-tracing
  ROLE: CoversRelease
- TYPE: Parent
  VALUE: RELEASE-rel-r1-platform-followups
  ROLE: CoversRelease
- TYPE: Parent
  VALUE: RELEASE-rel-r1-read-contracts
  ROLE: CoversRelease
- TYPE: Parent
  VALUE: RELEASE-rel-r1-read-hierarchy
  ROLE: CoversRelease
- TYPE: Parent
  VALUE: RELEASE-rel-r1-read-releases
  ROLE: CoversRelease
- TYPE: Parent
  VALUE: RELEASE-rel-r1-read-requirements
  ROLE: CoversRelease
- TYPE: Parent
  VALUE: RELEASE-rel-r1-relations-api
  ROLE: CoversRelease
- TYPE: Parent
  VALUE: RELEASE-rel-r1-rename-reqalm
  ROLE: CoversRelease
- TYPE: Parent
  VALUE: RELEASE-rel-r1-reqalm-contracts
  ROLE: CoversRelease
- TYPE: Parent
  VALUE: RELEASE-rel-r1-route-hardening
  ROLE: CoversRelease
- TYPE: Parent
  VALUE: RELEASE-rel-r1-route-helper
  ROLE: CoversRelease
- TYPE: Parent
  VALUE: RELEASE-rel-r1-seed-attach-figma
  ROLE: CoversRelease
- TYPE: Parent
  VALUE: RELEASE-rel-r1-seed-grooming
  ROLE: CoversRelease
- TYPE: Parent
  VALUE: RELEASE-rel-r1-seed-reset
  ROLE: CoversRelease
- TYPE: Parent
  VALUE: RELEASE-rel-r1-service-foundation
  ROLE: CoversRelease
- TYPE: Parent
  VALUE: RELEASE-rel-r1-test-harness
  ROLE: CoversRelease
- TYPE: Parent
  VALUE: RELEASE-rel-r1-test-hygiene
  ROLE: CoversRelease
- TYPE: Parent
  VALUE: RELEASE-rel-r1-trace-inherit-uses
  ROLE: CoversRelease
- TYPE: Parent
  VALUE: RELEASE-rel-r1-ui-header-nav
  ROLE: CoversRelease
- TYPE: Parent
  VALUE: RELEASE-rel-r1-ui-layout-capabilities
  ROLE: CoversRelease

[REQUIREMENT]
UID: CONTRACT-ctr-reqalm-maintenance
STATUS: Active
TITLE: Contract ReqALM maintenance
STATEMENT: >>>
ReqALM contract overlay `ReqALM maintenance` (status=active, starts_on=2026-10-09). Links requirement versions via in_scope_of; not a tree parent.
<<<
COMMENT: >>>
KIND: contract
contract_id: ctr-reqalm-maintenance
client_id: raby-family
project_id: reqalm
in_scope_of: CAP-UPKEEP-MONTHLY-SEC-AUDIT, CAP-UPKEEP-MONTHLY-DEPS-VULN, CAP-UPKEEP-QUARTERLY-ACCESS-RECERT, CAP-UPKEEP-AUDIT-LOG-REVIEW
in_scope_of_count: 4
covers_releases: (none)
covers_releases_count: 0
<<<
RELATIONS:
- TYPE: Parent
  VALUE: SEC-CONTRACTS-EXPORT
- TYPE: Parent
  VALUE: CAP-UPKEEP-MONTHLY-SEC-AUDIT
  ROLE: InScopeOf
- TYPE: Parent
  VALUE: CAP-UPKEEP-MONTHLY-DEPS-VULN
  ROLE: InScopeOf
- TYPE: Parent
  VALUE: CAP-UPKEEP-QUARTERLY-ACCESS-RECERT
  ROLE: InScopeOf
- TYPE: Parent
  VALUE: CAP-UPKEEP-AUDIT-LOG-REVIEW
  ROLE: InScopeOf

[[/SECTION]]

[[SECTION]]
UID: SEC-RELEASES-EXPORT
TITLE: Releases

[REQUIREMENT]
UID: RELEASE-rel-r0-sequences
STATUS: Active
TITLE: Release R0-sequences
STATEMENT: >>>
ReqALM release `R0-sequences` (status=shipped, planned_on=2026-10-15). delivers is a snapshot of requirement version UIDs.
<<<
COMMENT: >>>
KIND: release
release_id: rel-r0-sequences
project_id: reqalm
shipped_on: 2026-10-06
raw_status: shipped
delivers: A01, A02, A03, A04, A05, A06, A07, A08, ARCH-CP-HIER, ARCH-VER, ARCH-UI, ARCH-API, ARCH-OTEL, CAP-SSO, CAP-SCOPED-VIEW, CAP-RBAC, MC01.1, MC02
delivers_count: 18
<<<
RELATIONS:
- TYPE: Parent
  VALUE: SEC-RELEASES-EXPORT
- TYPE: Parent
  VALUE: A01
  ROLE: Delivers
- TYPE: Parent
  VALUE: A02
  ROLE: Delivers
- TYPE: Parent
  VALUE: A03
  ROLE: Delivers
- TYPE: Parent
  VALUE: A04
  ROLE: Delivers
- TYPE: Parent
  VALUE: A05
  ROLE: Delivers
- TYPE: Parent
  VALUE: A06
  ROLE: Delivers
- TYPE: Parent
  VALUE: A07
  ROLE: Delivers
- TYPE: Parent
  VALUE: A08
  ROLE: Delivers
- TYPE: Parent
  VALUE: ARCH-CP-HIER
  ROLE: Delivers
- TYPE: Parent
  VALUE: ARCH-VER
  ROLE: Delivers
- TYPE: Parent
  VALUE: ARCH-UI
  ROLE: Delivers
- TYPE: Parent
  VALUE: ARCH-API
  ROLE: Delivers
- TYPE: Parent
  VALUE: ARCH-OTEL
  ROLE: Delivers
- TYPE: Parent
  VALUE: CAP-SSO
  ROLE: Delivers
- TYPE: Parent
  VALUE: CAP-SCOPED-VIEW
  ROLE: Delivers
- TYPE: Parent
  VALUE: CAP-RBAC
  ROLE: Delivers
- TYPE: Parent
  VALUE: MC01.1
  ROLE: Delivers
- TYPE: Parent
  VALUE: MC02
  ROLE: Delivers

[REQUIREMENT]
UID: RELEASE-rel-pr11-planning-baseline
STATUS: Active
TITLE: Release PR #11 — planning baseline
STATEMENT: >>>
ReqALM release `PR #11 — planning baseline` (status=shipped, planned_on=2026-10-07). delivers is a snapshot of requirement version UIDs.
<<<
COMMENT: >>>
KIND: release
release_id: rel-pr11-planning-baseline
project_id: reqalm
shipped_on: 2026-10-07
raw_status: shipped
delivers: (none)
delivers_count: 0
<<<
RELATIONS:
- TYPE: Parent
  VALUE: SEC-RELEASES-EXPORT

[REQUIREMENT]
UID: RELEASE-rel-pr12-devenv-foundation
STATUS: Active
TITLE: Release PR #12 — devenv foundation
STATEMENT: >>>
ReqALM release `PR #12 — devenv foundation` (status=shipped, planned_on=2026-10-07). delivers is a snapshot of requirement version UIDs.
<<<
COMMENT: >>>
KIND: release
release_id: rel-pr12-devenv-foundation
project_id: reqalm
shipped_on: 2026-10-07
raw_status: shipped
delivers: ARCH-DEVENV-MODES.1, ARCH-DEVENV-PARITY.1, ARCH-DEVENV-KEYS, ARCH-DEVENV-CLONE, ARCH-DEVENV-SEED, ARCH-DEVENV-SECRETS, ARCH-DEVENV-HEALTH, M04, FIX-ALLOW-DEVENV-SMOKE, FIX-ALLOW-DEVENV-SEED-IDEMPOTENT, CAP-DEVENV-MONOREPO, CAP-DEVENV-DOC...
delivers_count: 22
<<<
RELATIONS:
- TYPE: Parent
  VALUE: SEC-RELEASES-EXPORT
- TYPE: Parent
  VALUE: ARCH-DEVENV-MODES.1
  ROLE: Delivers
- TYPE: Parent
  VALUE: ARCH-DEVENV-PARITY.1
  ROLE: Delivers
- TYPE: Parent
  VALUE: ARCH-DEVENV-KEYS
  ROLE: Delivers
- TYPE: Parent
  VALUE: ARCH-DEVENV-CLONE
  ROLE: Delivers
- TYPE: Parent
  VALUE: ARCH-DEVENV-SEED
  ROLE: Delivers
- TYPE: Parent
  VALUE: ARCH-DEVENV-SECRETS
  ROLE: Delivers
- TYPE: Parent
  VALUE: ARCH-DEVENV-HEALTH
  ROLE: Delivers
- TYPE: Parent
  VALUE: M04
  ROLE: Delivers
- TYPE: Parent
  VALUE: FIX-ALLOW-DEVENV-SMOKE
  ROLE: Delivers
- TYPE: Parent
  VALUE: FIX-ALLOW-DEVENV-SEED-IDEMPOTENT
  ROLE: Delivers
- TYPE: Parent
  VALUE: CAP-DEVENV-MONOREPO
  ROLE: Delivers
- TYPE: Parent
  VALUE: CAP-DEVENV-DOCKERFILE-ROLES
  ROLE: Delivers
- TYPE: Parent
  VALUE: CAP-DEVENV-PERIPHERALS
  ROLE: Delivers
- TYPE: Parent
  VALUE: CAP-DEVENV-COMPOSE
  ROLE: Delivers
- TYPE: Parent
  VALUE: CAP-HEALTH-LIVENESS
  ROLE: Delivers
- TYPE: Parent
  VALUE: CAP-READY-PROBES
  ROLE: Delivers
- TYPE: Parent
  VALUE: CAP-DEVENV-STARTUP-BACKOFF
  ROLE: Delivers
- TYPE: Parent
  VALUE: CAP-PROD-SELFCHECK
  ROLE: Delivers
- TYPE: Parent
  VALUE: CAP-DEVENV-OPENBAO-BOOTSTRAP
  ROLE: Delivers
- TYPE: Parent
  VALUE: CAP-DEVENV-MIGRATE-SEED
  ROLE: Delivers
- TYPE: Parent
  VALUE: CAP-API-DOCS-SEED-SUMMARY
  ROLE: Delivers
- TYPE: Parent
  VALUE: CAP-DEVENV-SMOKE
  ROLE: Delivers

[REQUIREMENT]
UID: RELEASE-rel-r1-foundation-shell-auth
STATUS: Active
TITLE: Release R1 — foundation shell + internal auth
STATEMENT: >>>
ReqALM release `R1 — foundation shell + internal auth` (status=shipped, planned_on=2026-10-07). delivers is a snapshot of requirement version UIDs.
<<<
COMMENT: >>>
KIND: release
release_id: rel-r1-foundation-shell-auth
project_id: reqalm
shipped_on: 2026-10-07
raw_status: shipped
delivers: ARCH-API-RBAC, ARCH-AUTH-AGENT-ATTRIBUTION, ARCH-AUTH-AS, ARCH-AUTH-AUDIENCE, ARCH-AUTH-CLIENTREG, ARCH-AUTH-LOCAL.1, ARCH-AUTH-MCP-REQUIRED, ARCH-AUTH-METADATA, ARCH-AUTH-PKCE, ARCH-AUTH-PROFILE, ARCH-AUTH-REFRESH, ARCH-AUTH-REVOKE, ARC...
delivers_count: 40
<<<
RELATIONS:
- TYPE: Parent
  VALUE: SEC-RELEASES-EXPORT
- TYPE: Parent
  VALUE: ARCH-API-RBAC
  ROLE: Delivers
- TYPE: Parent
  VALUE: ARCH-AUTH-AGENT-ATTRIBUTION
  ROLE: Delivers
- TYPE: Parent
  VALUE: ARCH-AUTH-AS
  ROLE: Delivers
- TYPE: Parent
  VALUE: ARCH-AUTH-AUDIENCE
  ROLE: Delivers
- TYPE: Parent
  VALUE: ARCH-AUTH-CLIENTREG
  ROLE: Delivers
- TYPE: Parent
  VALUE: ARCH-AUTH-LOCAL.1
  ROLE: Delivers
- TYPE: Parent
  VALUE: ARCH-AUTH-MCP-REQUIRED
  ROLE: Delivers
- TYPE: Parent
  VALUE: ARCH-AUTH-METADATA
  ROLE: Delivers
- TYPE: Parent
  VALUE: ARCH-AUTH-PKCE
  ROLE: Delivers
- TYPE: Parent
  VALUE: ARCH-AUTH-PROFILE
  ROLE: Delivers
- TYPE: Parent
  VALUE: ARCH-AUTH-REFRESH
  ROLE: Delivers
- TYPE: Parent
  VALUE: ARCH-AUTH-REVOKE
  ROLE: Delivers
- TYPE: Parent
  VALUE: ARCH-AUTH-UPSTREAM-CONNECTOR
  ROLE: Delivers
- TYPE: Parent
  VALUE: ARCH-BUILD-FOUNDATION
  ROLE: Delivers
- TYPE: Parent
  VALUE: ARCH-CRED
  ROLE: Delivers
- TYPE: Parent
  VALUE: ARCH-CRED-AUDIT
  ROLE: Delivers
- TYPE: Parent
  VALUE: ARCH-CRED-HASH
  ROLE: Delivers
- TYPE: Parent
  VALUE: ARCH-CRED-LOCKOUT
  ROLE: Delivers
- TYPE: Parent
  VALUE: ARCH-CRED-MFA
  ROLE: Delivers
- TYPE: Parent
  VALUE: ARCH-CRED-POLICY
  ROLE: Delivers
- TYPE: Parent
  VALUE: ARCH-CRED-TOKENS
  ROLE: Delivers
- TYPE: Parent
  VALUE: ARCH-DEVENV-IDENTITY.1
  ROLE: Delivers
- TYPE: Parent
  VALUE: ARCH-KEY
  ROLE: Delivers
- TYPE: Parent
  VALUE: ARCH-KEY-FAILCLOSED
  ROLE: Delivers
- TYPE: Parent
  VALUE: ARCH-KEY-JWKS
  ROLE: Delivers
- TYPE: Parent
  VALUE: ARCH-KEY-LIFECYCLE
  ROLE: Delivers
- TYPE: Parent
  VALUE: ARCH-KEY-PROVIDER
  ROLE: Delivers
- TYPE: Parent
  VALUE: ARCH-KEY-SCOPE
  ROLE: Delivers
- TYPE: Parent
  VALUE: ARCH-UI-GUARD
  ROLE: Delivers
- TYPE: Parent
  VALUE: CAP-AGENT-ACCESS
  ROLE: Delivers
- TYPE: Parent
  VALUE: CAP-AUTH-AUDIT
  ROLE: Delivers
- TYPE: Parent
  VALUE: CAP-AUTH-HARDEN
  ROLE: Delivers
- TYPE: Parent
  VALUE: CAP-AUTH-UPSTREAM-SEAM
  ROLE: Delivers
- TYPE: Parent
  VALUE: CAP-CRED-STORE
  ROLE: Delivers
- TYPE: Parent
  VALUE: CAP-DEVENV-INIT
  ROLE: Delivers
- TYPE: Parent
  VALUE: CAP-KEY-ENVELOPE
  ROLE: Delivers
- TYPE: Parent
  VALUE: CAP-MFA-ENROLL
  ROLE: Delivers
- TYPE: Parent
  VALUE: CAP-OAUTH-AS
  ROLE: Delivers
- TYPE: Parent
  VALUE: CAP-RBAC
  ROLE: Delivers
- TYPE: Parent
  VALUE: CAP-UI-FRAME
  ROLE: Delivers

[REQUIREMENT]
UID: RELEASE-rel-r1-core-alm
STATUS: Draft
TITLE: Release R1-core-ALM
STATEMENT: >>>
ReqALM release `R1-core-ALM` (status=planned, planned_on=2026-11-30). delivers is a snapshot of requirement version UIDs.
<<<
COMMENT: >>>
KIND: release
release_id: rel-r1-core-alm
project_id: reqalm
shipped_on: None
raw_status: planned
delivers: A09, A10, A11, A12.1, B01, B04, B05, B07, B08, C01, C02, C03, C06, C08, D01, D02, D03, D04, D05, D06, D08, D09, E01, E02, E04, E06, F01, F04, F07, F10, G01, G03, G05, G08, H06, H09, I01, I03, J01, J02, J07, K01, K03, K05, L01, L02, L04, ...
delivers_count: 96
<<<
RELATIONS:
- TYPE: Parent
  VALUE: SEC-RELEASES-EXPORT
- TYPE: Parent
  VALUE: A09
  ROLE: Delivers
- TYPE: Parent
  VALUE: A10
  ROLE: Delivers
- TYPE: Parent
  VALUE: A11
  ROLE: Delivers
- TYPE: Parent
  VALUE: A12.1
  ROLE: Delivers
- TYPE: Parent
  VALUE: B01
  ROLE: Delivers
- TYPE: Parent
  VALUE: B04
  ROLE: Delivers
- TYPE: Parent
  VALUE: B05
  ROLE: Delivers
- TYPE: Parent
  VALUE: B07
  ROLE: Delivers
- TYPE: Parent
  VALUE: B08
  ROLE: Delivers
- TYPE: Parent
  VALUE: C01
  ROLE: Delivers
- TYPE: Parent
  VALUE: C02
  ROLE: Delivers
- TYPE: Parent
  VALUE: C03
  ROLE: Delivers
- TYPE: Parent
  VALUE: C06
  ROLE: Delivers
- TYPE: Parent
  VALUE: C08
  ROLE: Delivers
- TYPE: Parent
  VALUE: D01
  ROLE: Delivers
- TYPE: Parent
  VALUE: D02
  ROLE: Delivers
- TYPE: Parent
  VALUE: D03
  ROLE: Delivers
- TYPE: Parent
  VALUE: D04
  ROLE: Delivers
- TYPE: Parent
  VALUE: D05
  ROLE: Delivers
- TYPE: Parent
  VALUE: D06
  ROLE: Delivers
- TYPE: Parent
  VALUE: D08
  ROLE: Delivers
- TYPE: Parent
  VALUE: D09
  ROLE: Delivers
- TYPE: Parent
  VALUE: E01
  ROLE: Delivers
- TYPE: Parent
  VALUE: E02
  ROLE: Delivers
- TYPE: Parent
  VALUE: E04
  ROLE: Delivers
- TYPE: Parent
  VALUE: E06
  ROLE: Delivers
- TYPE: Parent
  VALUE: F01
  ROLE: Delivers
- TYPE: Parent
  VALUE: F04
  ROLE: Delivers
- TYPE: Parent
  VALUE: F07
  ROLE: Delivers
- TYPE: Parent
  VALUE: F10
  ROLE: Delivers
- TYPE: Parent
  VALUE: G01
  ROLE: Delivers
- TYPE: Parent
  VALUE: G03
  ROLE: Delivers
- TYPE: Parent
  VALUE: G05
  ROLE: Delivers
- TYPE: Parent
  VALUE: G08
  ROLE: Delivers
- TYPE: Parent
  VALUE: H06
  ROLE: Delivers
- TYPE: Parent
  VALUE: H09
  ROLE: Delivers
- TYPE: Parent
  VALUE: I01
  ROLE: Delivers
- TYPE: Parent
  VALUE: I03
  ROLE: Delivers
- TYPE: Parent
  VALUE: J01
  ROLE: Delivers
- TYPE: Parent
  VALUE: J02
  ROLE: Delivers
- TYPE: Parent
  VALUE: J07
  ROLE: Delivers
- TYPE: Parent
  VALUE: K01
  ROLE: Delivers
- TYPE: Parent
  VALUE: K03
  ROLE: Delivers
- TYPE: Parent
  VALUE: K05
  ROLE: Delivers
- TYPE: Parent
  VALUE: L01
  ROLE: Delivers
- TYPE: Parent
  VALUE: L02
  ROLE: Delivers
- TYPE: Parent
  VALUE: L04
  ROLE: Delivers
- TYPE: Parent
  VALUE: M01
  ROLE: Delivers
- TYPE: Parent
  VALUE: M04
  ROLE: Delivers
- TYPE: Parent
  VALUE: N01
  ROLE: Delivers
- TYPE: Parent
  VALUE: N03
  ROLE: Delivers
- TYPE: Parent
  VALUE: ARCH-CONTRACT
  ROLE: Delivers
- TYPE: Parent
  VALUE: ARCH-CONTRACT.1
  ROLE: Delivers
- TYPE: Parent
  VALUE: ARCH-RELEASE
  ROLE: Delivers
- TYPE: Parent
  VALUE: ARCH-VER-SUCC
  ROLE: Delivers
- TYPE: Parent
  VALUE: CAP-TREE
  ROLE: Delivers
- TYPE: Parent
  VALUE: CAP-CONTRACT-UI
  ROLE: Delivers
- TYPE: Parent
  VALUE: CAP-VERSION-UI
  ROLE: Delivers
- TYPE: Parent
  VALUE: CAP-AUDIT
  ROLE: Delivers
- TYPE: Parent
  VALUE: MC03
  ROLE: Delivers
- TYPE: Parent
  VALUE: FIX-REL-SNAP
  ROLE: Delivers
- TYPE: Parent
  VALUE: FIX-SUCC-2HOP.2
  ROLE: Delivers
- TYPE: Parent
  VALUE: D12
  ROLE: Delivers
- TYPE: Parent
  VALUE: ARCH-APPROVAL
  ROLE: Delivers
- TYPE: Parent
  VALUE: ARCH-CHANGESET
  ROLE: Delivers
- TYPE: Parent
  VALUE: ARCH-CYBER-GATE
  ROLE: Delivers
- TYPE: Parent
  VALUE: ARCH-VERIFICATION
  ROLE: Delivers
- TYPE: Parent
  VALUE: ARCH-LOCKED
  ROLE: Delivers
- TYPE: Parent
  VALUE: M05
  ROLE: Delivers
- TYPE: Parent
  VALUE: M06
  ROLE: Delivers
- TYPE: Parent
  VALUE: FIX-DENY-PRIORITY-UNAPPROVED
  ROLE: Delivers
- TYPE: Parent
  VALUE: ARCH-MINT-KIND
  ROLE: Delivers
- TYPE: Parent
  VALUE: ARCH-SUSPECT.1
  ROLE: Delivers
- TYPE: Parent
  VALUE: ARCH-SUSPECT-QUEUE
  ROLE: Delivers
- TYPE: Parent
  VALUE: ARCH-GATE-SIGNOFF
  ROLE: Delivers
- TYPE: Parent
  VALUE: ARCH-SUCCESSION-HASH
  ROLE: Delivers
- TYPE: Parent
  VALUE: ARCH-WORKFLOW
  ROLE: Delivers
- TYPE: Parent
  VALUE: ARCH-APPROVAL-LINE
  ROLE: Delivers
- TYPE: Parent
  VALUE: ARCH-HOOK-EVAL
  ROLE: Delivers
- TYPE: Parent
  VALUE: ARCH-GATE-MODEL
  ROLE: Delivers
- TYPE: Parent
  VALUE: ARCH-APPROVER-SLOTS
  ROLE: Delivers
- TYPE: Parent
  VALUE: ARCH-CP-SCOPE
  ROLE: Delivers
- TYPE: Parent
  VALUE: FIX-DENY-NOOP-CONTENT
  ROLE: Delivers
- TYPE: Parent
  VALUE: FIX-DENY-SECOND-ACTIVE
  ROLE: Delivers
- TYPE: Parent
  VALUE: FIX-PLANNING-BLOCKED-AFTER-CONTENT-N
  ROLE: Delivers
- TYPE: Parent
  VALUE: FIX-GRANDFATHER-SEED-APPROVED
  ROLE: Delivers
- TYPE: Parent
  VALUE: FIX-SUSPECT-ON-CONTENT-N
  ROLE: Delivers
- TYPE: Parent
  VALUE: FIX-DENY-AUTHOR-PIN-APPLY
  ROLE: Delivers
- TYPE: Parent
  VALUE: FIX-ALLOW-PIN-REQUEST
  ROLE: Delivers
- TYPE: Parent
  VALUE: FIX-ALLOW-SECURITY-PIN-APPLY
  ROLE: Delivers
- TYPE: Parent
  VALUE: FIX-DENY-APPROVE-WITHOUT-SLOT
  ROLE: Delivers
- TYPE: Parent
  VALUE: FIX-ALLOW-APPROVE-LINE
  ROLE: Delivers
- TYPE: Parent
  VALUE: FIX-DENY-SHIP-UNSIGNED
  ROLE: Delivers
- TYPE: Parent
  VALUE: D13
  ROLE: Delivers
- TYPE: Parent
  VALUE: UI-APPROVE-LINE
  ROLE: Delivers
- TYPE: Parent
  VALUE: UI-APPROVE-TREE
  ROLE: Delivers

[REQUIREMENT]
UID: RELEASE-rel-r1-platform-followups
STATUS: Draft
TITLE: Release R1 platform follow-ups (deferred from foundation PR)
STATEMENT: >>>
ReqALM release `R1 platform follow-ups (deferred from foundation PR)` (status=planned, planned_on=2026-11-30). delivers is a snapshot of requirement version UIDs.
<<<
COMMENT: >>>
KIND: release
release_id: rel-r1-platform-followups
project_id: reqalm
shipped_on: None
raw_status: planned
delivers: ARCH-API-LAYERS, ARCH-AUTH-CLAIM-MAP, ARCH-AUTH-FEDERATION, ARCH-AUTH-LOCAL-BREAKGLASS, ARCH-AUTH-UPSTREAM-REVOKE, ARCH-CRED-REAUTH, ARCH-CRED-SESSION, ARCH-DEPLOY-MINIMAL, ARCH-DEPLOY-PERIPHERALS, ARCH-DEVENV-COMPOSE.1, ARCH-KEY-BREAKGL...
delivers_count: 13
<<<
RELATIONS:
- TYPE: Parent
  VALUE: SEC-RELEASES-EXPORT
- TYPE: Parent
  VALUE: ARCH-API-LAYERS
  ROLE: Delivers
- TYPE: Parent
  VALUE: ARCH-AUTH-CLAIM-MAP
  ROLE: Delivers
- TYPE: Parent
  VALUE: ARCH-AUTH-FEDERATION
  ROLE: Delivers
- TYPE: Parent
  VALUE: ARCH-AUTH-LOCAL-BREAKGLASS
  ROLE: Delivers
- TYPE: Parent
  VALUE: ARCH-AUTH-UPSTREAM-REVOKE
  ROLE: Delivers
- TYPE: Parent
  VALUE: ARCH-CRED-REAUTH
  ROLE: Delivers
- TYPE: Parent
  VALUE: ARCH-CRED-SESSION
  ROLE: Delivers
- TYPE: Parent
  VALUE: ARCH-DEPLOY-MINIMAL
  ROLE: Delivers
- TYPE: Parent
  VALUE: ARCH-DEPLOY-PERIPHERALS
  ROLE: Delivers
- TYPE: Parent
  VALUE: ARCH-DEVENV-COMPOSE.1
  ROLE: Delivers
- TYPE: Parent
  VALUE: ARCH-KEY-BREAKGLASS
  ROLE: Delivers
- TYPE: Parent
  VALUE: ARCH-KEY-CUSTODIAN
  ROLE: Delivers
- TYPE: Parent
  VALUE: ARCH-KEY-FIPS
  ROLE: Delivers

[REQUIREMENT]
UID: RELEASE-rel-r1-test-harness
STATUS: Active
TITLE: Release R1 — in-process test harness (no Docker)
STATEMENT: >>>
ReqALM release `R1 — in-process test harness (no Docker)` (status=shipped, planned_on=2026-10-07). delivers is a snapshot of requirement version UIDs.
<<<
COMMENT: >>>
KIND: release
release_id: rel-r1-test-harness
project_id: reqalm
shipped_on: 2026-10-07
raw_status: shipped
delivers: CAP-TEST-MEMORY-KEYPROVIDER, CAP-TEST-PGLITE-DB, CAP-TEST-AUTH-ROUTES, CAP-TEST-PNPM-GATE
delivers_count: 4
<<<
RELATIONS:
- TYPE: Parent
  VALUE: SEC-RELEASES-EXPORT
- TYPE: Parent
  VALUE: CAP-TEST-MEMORY-KEYPROVIDER
  ROLE: Delivers
- TYPE: Parent
  VALUE: CAP-TEST-PGLITE-DB
  ROLE: Delivers
- TYPE: Parent
  VALUE: CAP-TEST-AUTH-ROUTES
  ROLE: Delivers
- TYPE: Parent
  VALUE: CAP-TEST-PNPM-GATE
  ROLE: Delivers

[REQUIREMENT]
UID: RELEASE-rel-r1-test-hygiene
STATUS: Active
TITLE: Release R1 — test/build hygiene (Docker-free test follow-ups)
STATEMENT: >>>
ReqALM release `R1 — test/build hygiene (Docker-free test follow-ups)` (status=shipped, planned_on=2026-10-07). delivers is a snapshot of requirement version UIDs.
<<<
COMMENT: >>>
KIND: release
release_id: rel-r1-test-hygiene
project_id: reqalm
shipped_on: 2026-10-07
raw_status: shipped
delivers: CAP-TEST-PROD-BUILD-EXCLUDE, CAP-TEST-AUTH-HYGIENE, CAP-DEVENV-SMOKE-COMPOSE-ISOLATION
delivers_count: 3
<<<
RELATIONS:
- TYPE: Parent
  VALUE: SEC-RELEASES-EXPORT
- TYPE: Parent
  VALUE: CAP-TEST-PROD-BUILD-EXCLUDE
  ROLE: Delivers
- TYPE: Parent
  VALUE: CAP-TEST-AUTH-HYGIENE
  ROLE: Delivers
- TYPE: Parent
  VALUE: CAP-DEVENV-SMOKE-COMPOSE-ISOLATION
  ROLE: Delivers

[REQUIREMENT]
UID: RELEASE-rel-r1-rename-reqalm
STATUS: Active
TITLE: Release R1 — product rename ReqALM
STATEMENT: >>>
ReqALM release `R1 — product rename ReqALM` (status=shipped, planned_on=2026-10-07). delivers is a snapshot of requirement version UIDs.
<<<
COMMENT: >>>
KIND: release
release_id: rel-r1-rename-reqalm
project_id: reqalm
shipped_on: 2026-10-07
raw_status: shipped
delivers: CAP-RENAME-REQALM
delivers_count: 1
<<<
RELATIONS:
- TYPE: Parent
  VALUE: SEC-RELEASES-EXPORT
- TYPE: Parent
  VALUE: CAP-RENAME-REQALM
  ROLE: Delivers

[REQUIREMENT]
UID: RELEASE-rel-r1-service-foundation
STATUS: Active
TITLE: Release R1 — API service foundation (context, RBAC ops, audit, envelope)
STATEMENT: >>>
ReqALM release `R1 — API service foundation (context, RBAC ops, audit, envelope)` (status=shipped, planned_on=2026-10-07). delivers is a snapshot of requirement version UIDs.
<<<
COMMENT: >>>
KIND: release
release_id: rel-r1-service-foundation
project_id: reqalm
shipped_on: 2026-10-07
raw_status: shipped
delivers: CAP-SVC-RESULT-ENVELOPE, CAP-SVC-REQUEST-CONTEXT, CAP-SVC-OPERATION-EXECUTOR, CAP-SVC-AUDIT-APPEND, CAP-SVC-STRUCTURED-LOG, CAP-SVC-ROUTE-REGISTRY, CAP-SVC-MODULE-BOOTSTRAP, CAP-SVC-PROJECT-READ
delivers_count: 8
<<<
RELATIONS:
- TYPE: Parent
  VALUE: SEC-RELEASES-EXPORT
- TYPE: Parent
  VALUE: CAP-SVC-RESULT-ENVELOPE
  ROLE: Delivers
- TYPE: Parent
  VALUE: CAP-SVC-REQUEST-CONTEXT
  ROLE: Delivers
- TYPE: Parent
  VALUE: CAP-SVC-OPERATION-EXECUTOR
  ROLE: Delivers
- TYPE: Parent
  VALUE: CAP-SVC-AUDIT-APPEND
  ROLE: Delivers
- TYPE: Parent
  VALUE: CAP-SVC-STRUCTURED-LOG
  ROLE: Delivers
- TYPE: Parent
  VALUE: CAP-SVC-ROUTE-REGISTRY
  ROLE: Delivers
- TYPE: Parent
  VALUE: CAP-SVC-MODULE-BOOTSTRAP
  ROLE: Delivers
- TYPE: Parent
  VALUE: CAP-SVC-PROJECT-READ
  ROLE: Delivers

[REQUIREMENT]
UID: RELEASE-rel-r1-otel-tracing
STATUS: Active
TITLE: Release R1 — OpenTelemetry tracing (W3C, operation + dependency spans)
STATEMENT: >>>
ReqALM release `R1 — OpenTelemetry tracing (W3C, operation + dependency spans)` (status=shipped, planned_on=2026-10-07). delivers is a snapshot of requirement version UIDs.
<<<
COMMENT: >>>
KIND: release
release_id: rel-r1-otel-tracing
project_id: reqalm
shipped_on: 2026-10-07
raw_status: shipped
delivers: CAP-OTEL-SDK-BOOTSTRAP, CAP-OTEL-W3C-CONTEXT, CAP-OTEL-OPERATION-SPANS, CAP-OTEL-KEY-DEP, CAP-OTEL-AUDIT-TRACE, CAP-OTEL-EXPORT, CAP-OTEL-TEST-HARNESS
delivers_count: 7
<<<
RELATIONS:
- TYPE: Parent
  VALUE: SEC-RELEASES-EXPORT
- TYPE: Parent
  VALUE: CAP-OTEL-SDK-BOOTSTRAP
  ROLE: Delivers
- TYPE: Parent
  VALUE: CAP-OTEL-W3C-CONTEXT
  ROLE: Delivers
- TYPE: Parent
  VALUE: CAP-OTEL-OPERATION-SPANS
  ROLE: Delivers
- TYPE: Parent
  VALUE: CAP-OTEL-KEY-DEP
  ROLE: Delivers
- TYPE: Parent
  VALUE: CAP-OTEL-AUDIT-TRACE
  ROLE: Delivers
- TYPE: Parent
  VALUE: CAP-OTEL-EXPORT
  ROLE: Delivers
- TYPE: Parent
  VALUE: CAP-OTEL-TEST-HARNESS
  ROLE: Delivers

[REQUIREMENT]
UID: RELEASE-rel-r1-route-helper
STATUS: Active
TITLE: Release R1 — defineOperationRoute (single business-route pipeline)
STATEMENT: >>>
ReqALM release `R1 — defineOperationRoute (single business-route pipeline)` (status=shipped, planned_on=2026-10-07). delivers is a snapshot of requirement version UIDs.
<<<
COMMENT: >>>
KIND: release
release_id: rel-r1-route-helper
project_id: reqalm
shipped_on: 2026-10-07
raw_status: shipped
delivers: CAP-SVC-OPERATION-ROUTE, CAP-SVC-BUSINESS-ROUTE-AUDIT, CAP-SVC-PROBLEM-JSON
delivers_count: 3
<<<
RELATIONS:
- TYPE: Parent
  VALUE: SEC-RELEASES-EXPORT
- TYPE: Parent
  VALUE: CAP-SVC-OPERATION-ROUTE
  ROLE: Delivers
- TYPE: Parent
  VALUE: CAP-SVC-BUSINESS-ROUTE-AUDIT
  ROLE: Delivers
- TYPE: Parent
  VALUE: CAP-SVC-PROBLEM-JSON
  ROLE: Delivers

[REQUIREMENT]
UID: RELEASE-rel-r1-route-hardening
STATUS: Active
TITLE: Release R1 — route helper hardening (Cyber/QA follow-up)
STATEMENT: >>>
ReqALM release `R1 — route helper hardening (Cyber/QA follow-up)` (status=shipped, planned_on=2026-10-07). delivers is a snapshot of requirement version UIDs.
<<<
COMMENT: >>>
KIND: release
release_id: rel-r1-route-hardening
project_id: reqalm
shipped_on: 2026-10-07
raw_status: shipped
delivers: CAP-SVC-PROJECT-ID-SLUG, CAP-SVC-STATIC-DEP-PATCH, CAP-OTEL-SPAN-SAFE-ERRORS, CAP-SVC-IMPLICIT-PUBLIC-EXACT, CAP-SVC-NON-API-AUTH-AUDIT
delivers_count: 5
<<<
RELATIONS:
- TYPE: Parent
  VALUE: SEC-RELEASES-EXPORT
- TYPE: Parent
  VALUE: CAP-SVC-PROJECT-ID-SLUG
  ROLE: Delivers
- TYPE: Parent
  VALUE: CAP-SVC-STATIC-DEP-PATCH
  ROLE: Delivers
- TYPE: Parent
  VALUE: CAP-OTEL-SPAN-SAFE-ERRORS
  ROLE: Delivers
- TYPE: Parent
  VALUE: CAP-SVC-IMPLICIT-PUBLIC-EXACT
  ROLE: Delivers
- TYPE: Parent
  VALUE: CAP-SVC-NON-API-AUTH-AUDIT
  ROLE: Delivers

[REQUIREMENT]
UID: RELEASE-rel-r1-seed-reset
STATUS: Active
TITLE: Release R1 — dev dogfood seed reset (pnpm devenv:seed:reset)
STATEMENT: >>>
ReqALM release `R1 — dev dogfood seed reset (pnpm devenv:seed:reset)` (status=shipped, planned_on=2026-10-07). delivers is a snapshot of requirement version UIDs.
<<<
COMMENT: >>>
KIND: release
release_id: rel-r1-seed-reset
project_id: reqalm
shipped_on: 2026-10-08
raw_status: shipped
delivers: CAP-DEVENV-SEED-RESET
delivers_count: 1
<<<
RELATIONS:
- TYPE: Parent
  VALUE: SEC-RELEASES-EXPORT
- TYPE: Parent
  VALUE: CAP-DEVENV-SEED-RESET
  ROLE: Delivers

[REQUIREMENT]
UID: RELEASE-rel-r1-browse-clients-projects
STATUS: Active
TITLE: Release R1 — browse clients and projects (read-only)
STATEMENT: >>>
ReqALM release `R1 — browse clients and projects (read-only)` (status=shipped, planned_on=2026-10-08). delivers is a snapshot of requirement version UIDs.
<<<
COMMENT: >>>
KIND: release
release_id: rel-r1-browse-clients-projects
project_id: reqalm
shipped_on: 2026-10-08
raw_status: shipped
delivers: CAP-BROWSE-CP
delivers_count: 1
<<<
RELATIONS:
- TYPE: Parent
  VALUE: SEC-RELEASES-EXPORT
- TYPE: Parent
  VALUE: CAP-BROWSE-CP
  ROLE: Delivers

[REQUIREMENT]
UID: RELEASE-rel-r1-browse-ui-cp
STATUS: Active
TITLE: Release R1 — browse clients and projects UI (read-only)
STATEMENT: >>>
ReqALM release `R1 — browse clients and projects UI (read-only)` (status=shipped, planned_on=2026-10-08). delivers is a snapshot of requirement version UIDs.
<<<
COMMENT: >>>
KIND: release
release_id: rel-r1-browse-ui-cp
project_id: reqalm
shipped_on: 2026-10-08
raw_status: shipped
delivers: CAP-BROWSE-UI-CP
delivers_count: 1
<<<
RELATIONS:
- TYPE: Parent
  VALUE: SEC-RELEASES-EXPORT
- TYPE: Parent
  VALUE: CAP-BROWSE-UI-CP
  ROLE: Delivers

[REQUIREMENT]
UID: RELEASE-rel-r1-read-requirements
STATUS: Active
TITLE: Release R1 — requirements read API
STATEMENT: >>>
ReqALM release `R1 — requirements read API` (status=shipped, planned_on=2026-10-08). delivers is a snapshot of requirement version UIDs.
<<<
COMMENT: >>>
KIND: release
release_id: rel-r1-read-requirements
project_id: reqalm
shipped_on: 2026-10-08
raw_status: shipped
delivers: CAP-READ-REQS
delivers_count: 1
<<<
RELATIONS:
- TYPE: Parent
  VALUE: SEC-RELEASES-EXPORT
- TYPE: Parent
  VALUE: CAP-READ-REQS
  ROLE: Delivers

[REQUIREMENT]
UID: RELEASE-rel-r1-browse-ui-reqs
STATUS: Active
TITLE: Release R1 — browse requirements UI (read-only)
STATEMENT: >>>
ReqALM release `R1 — browse requirements UI (read-only)` (status=shipped, planned_on=2026-10-08). delivers is a snapshot of requirement version UIDs.
<<<
COMMENT: >>>
KIND: release
release_id: rel-r1-browse-ui-reqs
project_id: reqalm
shipped_on: 2026-10-08
raw_status: shipped
delivers: CAP-BROWSE-UI-REQS
delivers_count: 1
<<<
RELATIONS:
- TYPE: Parent
  VALUE: SEC-RELEASES-EXPORT
- TYPE: Parent
  VALUE: CAP-BROWSE-UI-REQS
  ROLE: Delivers

[REQUIREMENT]
UID: RELEASE-rel-r1-read-releases
STATUS: Active
TITLE: Release R1 — releases read API
STATEMENT: >>>
ReqALM release `R1 — releases read API` (status=shipped, planned_on=2026-10-08). delivers is a snapshot of requirement version UIDs.
<<<
COMMENT: >>>
KIND: release
release_id: rel-r1-read-releases
project_id: reqalm
shipped_on: 2026-10-08
raw_status: shipped
delivers: CAP-READ-RELEASES
delivers_count: 1
<<<
RELATIONS:
- TYPE: Parent
  VALUE: SEC-RELEASES-EXPORT
- TYPE: Parent
  VALUE: CAP-READ-RELEASES
  ROLE: Delivers

[REQUIREMENT]
UID: RELEASE-rel-r1-browse-ui-releases
STATUS: Active
TITLE: Release R1 — browse releases UI (read-only)
STATEMENT: >>>
ReqALM release `R1 — browse releases UI (read-only)` (status=shipped, planned_on=2026-10-08). delivers is a snapshot of requirement version UIDs.
<<<
COMMENT: >>>
KIND: release
release_id: rel-r1-browse-ui-releases
project_id: reqalm
shipped_on: 2026-10-08
raw_status: shipped
delivers: CAP-BROWSE-UI-RELEASES
delivers_count: 1
<<<
RELATIONS:
- TYPE: Parent
  VALUE: SEC-RELEASES-EXPORT
- TYPE: Parent
  VALUE: CAP-BROWSE-UI-RELEASES
  ROLE: Delivers

[REQUIREMENT]
UID: RELEASE-rel-r1-read-hierarchy
STATUS: Active
TITLE: Release R1 — requirement hierarchy read API
STATEMENT: >>>
ReqALM release `R1 — requirement hierarchy read API` (status=shipped, planned_on=2026-10-08). delivers is a snapshot of requirement version UIDs.
<<<
COMMENT: >>>
KIND: release
release_id: rel-r1-read-hierarchy
project_id: reqalm
shipped_on: 2026-10-08
raw_status: shipped
delivers: CAP-READ-HIERARCHY
delivers_count: 1
<<<
RELATIONS:
- TYPE: Parent
  VALUE: SEC-RELEASES-EXPORT
- TYPE: Parent
  VALUE: CAP-READ-HIERARCHY
  ROLE: Delivers

[REQUIREMENT]
UID: RELEASE-rel-r1-browse-ui-tree
STATUS: Active
TITLE: Release R1 — browse requirements tree UI (read-only)
STATEMENT: >>>
ReqALM release `R1 — browse requirements tree UI (read-only)` (status=shipped, planned_on=2026-10-08). delivers is a snapshot of requirement version UIDs.
<<<
COMMENT: >>>
KIND: release
release_id: rel-r1-browse-ui-tree
project_id: reqalm
shipped_on: 2026-10-08
raw_status: shipped
delivers: CAP-BROWSE-UI-TREE
delivers_count: 1
<<<
RELATIONS:
- TYPE: Parent
  VALUE: SEC-RELEASES-EXPORT
- TYPE: Parent
  VALUE: CAP-BROWSE-UI-TREE
  ROLE: Delivers

[REQUIREMENT]
UID: RELEASE-rel-r1-mfa-qr
STATUS: Active
TITLE: Release R1 — MFA enrollment QR (sign-in UI)
STATEMENT: >>>
ReqALM release `R1 — MFA enrollment QR (sign-in UI)` (status=shipped, planned_on=2026-10-08). delivers is a snapshot of requirement version UIDs.
<<<
COMMENT: >>>
KIND: release
release_id: rel-r1-mfa-qr
project_id: reqalm
shipped_on: 2026-10-08
raw_status: shipped
delivers: CAP-MFA-QR
delivers_count: 1
<<<
RELATIONS:
- TYPE: Parent
  VALUE: SEC-RELEASES-EXPORT
- TYPE: Parent
  VALUE: CAP-MFA-QR
  ROLE: Delivers

[REQUIREMENT]
UID: RELEASE-rel-r1-relations-api
STATUS: Active
TITLE: Release R1 — requirement relations read API
STATEMENT: >>>
ReqALM release `R1 — requirement relations read API` (status=shipped, planned_on=2026-10-09). delivers is a snapshot of requirement version UIDs.
<<<
COMMENT: >>>
KIND: release
release_id: rel-r1-relations-api
project_id: reqalm
shipped_on: 2026-10-09
raw_status: shipped
delivers: CAP-RELATIONS-API
delivers_count: 1
<<<
RELATIONS:
- TYPE: Parent
  VALUE: SEC-RELEASES-EXPORT
- TYPE: Parent
  VALUE: CAP-RELATIONS-API
  ROLE: Delivers

[REQUIREMENT]
UID: RELEASE-rel-r1-seed-grooming
STATUS: Draft
TITLE: Release R1 — dogfood seed grooming
STATEMENT: >>>
ReqALM release `R1 — dogfood seed grooming` (status=planned, planned_on=2026-10-06). delivers is a snapshot of requirement version UIDs.
<<<
COMMENT: >>>
KIND: release
release_id: rel-r1-seed-grooming
project_id: reqalm
shipped_on: None
raw_status: planned
delivers: CAP-SEED-GROOMING
delivers_count: 1
<<<
RELATIONS:
- TYPE: Parent
  VALUE: SEC-RELEASES-EXPORT
- TYPE: Parent
  VALUE: CAP-SEED-GROOMING
  ROLE: Delivers

[REQUIREMENT]
UID: RELEASE-rel-r1-lf-endings
STATUS: Active
TITLE: Release R1 — Git LF line endings (Compose entrypoints)
STATEMENT: >>>
ReqALM release `R1 — Git LF line endings (Compose entrypoints)` (status=shipped, planned_on=2026-10-09). delivers is a snapshot of requirement version UIDs.
<<<
COMMENT: >>>
KIND: release
release_id: rel-r1-lf-endings
project_id: reqalm
shipped_on: 2026-10-09
raw_status: shipped
delivers: CAP-DEVENV-LF-ENDINGS
delivers_count: 1
<<<
RELATIONS:
- TYPE: Parent
  VALUE: SEC-RELEASES-EXPORT
- TYPE: Parent
  VALUE: CAP-DEVENV-LF-ENDINGS
  ROLE: Delivers

[REQUIREMENT]
UID: RELEASE-rel-r1-catalogs-api
STATUS: Active
TITLE: Release R1 — catalogs read API
STATEMENT: >>>
ReqALM release `R1 — catalogs read API` (status=shipped, planned_on=2026-10-09). delivers is a snapshot of requirement version UIDs.
<<<
COMMENT: >>>
KIND: release
release_id: rel-r1-catalogs-api
project_id: reqalm
shipped_on: 2026-10-09
raw_status: shipped
delivers: CAP-CATALOGS-API
delivers_count: 1
<<<
RELATIONS:
- TYPE: Parent
  VALUE: SEC-RELEASES-EXPORT
- TYPE: Parent
  VALUE: CAP-CATALOGS-API
  ROLE: Delivers

[REQUIREMENT]
UID: RELEASE-rel-r1-browse-ui-relations
STATUS: Active
TITLE: Release R1 — browse requirement relationships UI (read-only)
STATEMENT: >>>
ReqALM release `R1 — browse requirement relationships UI (read-only)` (status=shipped, planned_on=2026-10-09). delivers is a snapshot of requirement version UIDs.
<<<
COMMENT: >>>
KIND: release
release_id: rel-r1-browse-ui-relations
project_id: reqalm
shipped_on: 2026-10-09
raw_status: shipped
delivers: CAP-BROWSE-UI-RELATIONS
delivers_count: 1
<<<
RELATIONS:
- TYPE: Parent
  VALUE: SEC-RELEASES-EXPORT
- TYPE: Parent
  VALUE: CAP-BROWSE-UI-RELATIONS
  ROLE: Delivers

[REQUIREMENT]
UID: RELEASE-rel-r1-ui-header-nav
STATUS: Active
TITLE: Release R1 — ReqALM header and project navigation
STATEMENT: >>>
ReqALM release `R1 — ReqALM header and project navigation` (status=shipped, planned_on=2026-10-09). delivers is a snapshot of requirement version UIDs.
<<<
COMMENT: >>>
KIND: release
release_id: rel-r1-ui-header-nav
project_id: reqalm
shipped_on: 2026-10-09
raw_status: shipped
delivers: CAP-UI-HEADER-NAV
delivers_count: 1
<<<
RELATIONS:
- TYPE: Parent
  VALUE: SEC-RELEASES-EXPORT
- TYPE: Parent
  VALUE: CAP-UI-HEADER-NAV
  ROLE: Delivers

[REQUIREMENT]
UID: RELEASE-rel-r1-reqalm-contracts
STATUS: Active
TITLE: Release R1 — ReqALM product and maintenance contracts (seed)
STATEMENT: >>>
ReqALM release `R1 — ReqALM product and maintenance contracts (seed)` (status=shipped, planned_on=2026-10-09). delivers is a snapshot of requirement version UIDs.
<<<
COMMENT: >>>
KIND: release
release_id: rel-r1-reqalm-contracts
project_id: reqalm
shipped_on: 2026-10-09
raw_status: shipped
delivers: CAP-REQALM-CONTRACTS
delivers_count: 1
<<<
RELATIONS:
- TYPE: Parent
  VALUE: SEC-RELEASES-EXPORT
- TYPE: Parent
  VALUE: CAP-REQALM-CONTRACTS
  ROLE: Delivers

[REQUIREMENT]
UID: RELEASE-rel-r1-trace-inherit-uses
STATUS: Active
TITLE: Release R1 — trace inheritable controls over uses
STATEMENT: >>>
ReqALM release `R1 — trace inheritable controls over uses` (status=shipped, planned_on=2026-10-09). delivers is a snapshot of requirement version UIDs.
<<<
COMMENT: >>>
KIND: release
release_id: rel-r1-trace-inherit-uses
project_id: reqalm
shipped_on: 2026-10-09
raw_status: shipped
delivers: CAP-TRACE-INHERIT-USES
delivers_count: 1
<<<
RELATIONS:
- TYPE: Parent
  VALUE: SEC-RELEASES-EXPORT
- TYPE: Parent
  VALUE: CAP-TRACE-INHERIT-USES
  ROLE: Delivers

[REQUIREMENT]
UID: RELEASE-rel-r1-seed-attach-figma
STATUS: Active
TITLE: Release R1 — Cyber attachments + Figma requirements (seed)
STATEMENT: >>>
ReqALM release `R1 — Cyber attachments + Figma requirements (seed)` (status=shipped, planned_on=2026-10-10). delivers is a snapshot of requirement version UIDs.
<<<
COMMENT: >>>
KIND: release
release_id: rel-r1-seed-attach-figma
project_id: reqalm
shipped_on: 2026-10-09
raw_status: shipped
delivers: CAP-SEED-ATTACH-FIGMA
delivers_count: 1
<<<
RELATIONS:
- TYPE: Parent
  VALUE: SEC-RELEASES-EXPORT
- TYPE: Parent
  VALUE: CAP-SEED-ATTACH-FIGMA
  ROLE: Delivers

[REQUIREMENT]
UID: RELEASE-rel-r1-ui-layout-capabilities
STATUS: Active
TITLE: Release R1 — UI layout capability statements (seed)
STATEMENT: >>>
ReqALM release `R1 — UI layout capability statements (seed)` (status=shipped, planned_on=2026-10-10). delivers is a snapshot of requirement version UIDs.
<<<
COMMENT: >>>
KIND: release
release_id: rel-r1-ui-layout-capabilities
project_id: reqalm
shipped_on: 2026-10-09
raw_status: shipped
delivers: CAP-UI-LAYOUT
delivers_count: 1
<<<
RELATIONS:
- TYPE: Parent
  VALUE: SEC-RELEASES-EXPORT
- TYPE: Parent
  VALUE: CAP-UI-LAYOUT
  ROLE: Delivers

[REQUIREMENT]
UID: RELEASE-rel-r1-browse-ui-catalogs
STATUS: Active
TITLE: Release R1 — browse catalogs UI (read-only)
STATEMENT: >>>
ReqALM release `R1 — browse catalogs UI (read-only)` (status=shipped, planned_on=2026-10-09). delivers is a snapshot of requirement version UIDs.
<<<
COMMENT: >>>
KIND: release
release_id: rel-r1-browse-ui-catalogs
project_id: reqalm
shipped_on: 2026-10-09
raw_status: shipped
delivers: CAP-BROWSE-UI-CATALOGS
delivers_count: 1
<<<
RELATIONS:
- TYPE: Parent
  VALUE: SEC-RELEASES-EXPORT
- TYPE: Parent
  VALUE: CAP-BROWSE-UI-CATALOGS
  ROLE: Delivers

[REQUIREMENT]
UID: RELEASE-rel-r1-contracts-loader
STATUS: Active
TITLE: Release R1 — contracts loader (DB + seed)
STATEMENT: >>>
ReqALM release `R1 — contracts loader (DB + seed)` (status=shipped, planned_on=2026-10-10). delivers is a snapshot of requirement version UIDs.
<<<
COMMENT: >>>
KIND: release
release_id: rel-r1-contracts-loader
project_id: reqalm
shipped_on: 2026-10-10
raw_status: shipped
delivers: CAP-CONTRACTS-LOADER
delivers_count: 1
<<<
RELATIONS:
- TYPE: Parent
  VALUE: SEC-RELEASES-EXPORT
- TYPE: Parent
  VALUE: CAP-CONTRACTS-LOADER
  ROLE: Delivers

[REQUIREMENT]
UID: RELEASE-rel-r1-read-contracts
STATUS: Active
TITLE: Release R1 — contracts read API
STATEMENT: >>>
ReqALM release `R1 — contracts read API` (status=shipped, planned_on=2026-10-10). delivers is a snapshot of requirement version UIDs.
<<<
COMMENT: >>>
KIND: release
release_id: rel-r1-read-contracts
project_id: reqalm
shipped_on: 2026-10-10
raw_status: shipped
delivers: CAP-READ-CONTRACTS
delivers_count: 1
<<<
RELATIONS:
- TYPE: Parent
  VALUE: SEC-RELEASES-EXPORT
- TYPE: Parent
  VALUE: CAP-READ-CONTRACTS
  ROLE: Delivers

[REQUIREMENT]
UID: RELEASE-rel-r1-browse-ui-contracts
STATUS: Active
TITLE: Release R1 — browse contracts UI (read-only)
STATEMENT: >>>
ReqALM release `R1 — browse contracts UI (read-only)` (status=shipped, planned_on=2026-10-10). delivers is a snapshot of requirement version UIDs.
<<<
COMMENT: >>>
KIND: release
release_id: rel-r1-browse-ui-contracts
project_id: reqalm
shipped_on: 2026-10-10
raw_status: shipped
delivers: CAP-BROWSE-UI-CONTRACTS
delivers_count: 1
<<<
RELATIONS:
- TYPE: Parent
  VALUE: SEC-RELEASES-EXPORT
- TYPE: Parent
  VALUE: CAP-BROWSE-UI-CONTRACTS
  ROLE: Delivers

[REQUIREMENT]
UID: RELEASE-rel-r1-rbac-authorize-fail-closed
STATUS: Active
TITLE: Release R1 — RBAC authorize fail closed (no project scope)
STATEMENT: >>>
ReqALM release `R1 — RBAC authorize fail closed (no project scope)` (status=shipped, planned_on=2026-10-10). delivers is a snapshot of requirement version UIDs.
<<<
COMMENT: >>>
KIND: release
release_id: rel-r1-rbac-authorize-fail-closed
project_id: reqalm
shipped_on: 2026-10-10
raw_status: shipped
delivers: CAP-SVC-RBAC-NO-PROJECT
delivers_count: 1
<<<
RELATIONS:
- TYPE: Parent
  VALUE: SEC-RELEASES-EXPORT
- TYPE: Parent
  VALUE: CAP-SVC-RBAC-NO-PROJECT
  ROLE: Delivers

[REQUIREMENT]
UID: RELEASE-rel-r1-planning-read-api
STATUS: Draft
TITLE: Release R1 — planning read API
STATEMENT: >>>
ReqALM release `R1 — planning read API` (status=planned, planned_on=2026-10-10). delivers is a snapshot of requirement version UIDs.
<<<
COMMENT: >>>
KIND: release
release_id: rel-r1-planning-read-api
project_id: reqalm
shipped_on: None
raw_status: planned
delivers: CAP-READ-PLANNING
delivers_count: 1
<<<
RELATIONS:
- TYPE: Parent
  VALUE: SEC-RELEASES-EXPORT
- TYPE: Parent
  VALUE: CAP-READ-PLANNING
  ROLE: Delivers

[REQUIREMENT]
UID: RELEASE-rel-r1-artifacts-read-api
STATUS: Draft
TITLE: Release R1 — capability artifacts read API
STATEMENT: >>>
ReqALM release `R1 — capability artifacts read API` (status=planned, planned_on=2026-10-10). delivers is a snapshot of requirement version UIDs.
<<<
COMMENT: >>>
KIND: release
release_id: rel-r1-artifacts-read-api
project_id: reqalm
shipped_on: None
raw_status: planned
delivers: CAP-READ-ARTIFACTS
delivers_count: 1
<<<
RELATIONS:
- TYPE: Parent
  VALUE: SEC-RELEASES-EXPORT
- TYPE: Parent
  VALUE: CAP-READ-ARTIFACTS
  ROLE: Delivers

[REQUIREMENT]
UID: RELEASE-rel-r1-hardening-followup-1
STATUS: Draft
TITLE: Release R1 — hardening follow-up (no-project gate, fetchAllScope, test kit)
STATEMENT: >>>
ReqALM release `R1 — hardening follow-up (no-project gate, fetchAllScope, test kit)` (status=planned, planned_on=2026-10-10). delivers is a snapshot of requirement version UIDs.
<<<
COMMENT: >>>
KIND: release
release_id: rel-r1-hardening-followup-1
project_id: reqalm
shipped_on: None
raw_status: planned
delivers: CAP-SVC-HARDENING-FOLLOWUP
delivers_count: 1
<<<
RELATIONS:
- TYPE: Parent
  VALUE: SEC-RELEASES-EXPORT
- TYPE: Parent
  VALUE: CAP-SVC-HARDENING-FOLLOWUP
  ROLE: Delivers

[REQUIREMENT]
UID: RELEASE-rel-r1-criteria-release-review
STATUS: Draft
TITLE: Release R1 — capability criteria completed in release review
STATEMENT: >>>
ReqALM release `R1 — capability criteria completed in release review` (status=planned, planned_on=2026-10-10). delivers is a snapshot of requirement version UIDs.
<<<
COMMENT: >>>
KIND: release
release_id: rel-r1-criteria-release-review
project_id: reqalm
shipped_on: None
raw_status: planned
delivers: CAP-CRITERIA-RELEASE-REVIEW
delivers_count: 1
<<<
RELATIONS:
- TYPE: Parent
  VALUE: SEC-RELEASES-EXPORT
- TYPE: Parent
  VALUE: CAP-CRITERIA-RELEASE-REVIEW
  ROLE: Delivers

[[/SECTION]]
