[DOCUMENT]
TITLE: STIGS
UID: CTRL-STIG
PREFIX: CTRL-STIG-
ROOT: False

[GRAMMAR]
ELEMENTS:
- TAG: TEXT
  FIELDS:
  - TITLE: STATEMENT
    TYPE: String
    REQUIRED: True
- TAG: SECTION
  FIELDS:
  - TITLE: UID
    TYPE: String
    REQUIRED: False
  - TITLE: TITLE
    TYPE: String
    REQUIRED: True
- TAG: REQUIREMENT
  FIELDS:
  - TITLE: UID
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  - TITLE: STATUS
    TYPE: SingleChoice(Draft, Active, Approved)
    REQUIRED: False
  RELATIONS:
  - TYPE: Parent
  - TYPE: Child
  - TYPE: File
  - TYPE: Parent
    ROLE: Refines
  - TYPE: Parent
    ROLE: Satisfies
  - TYPE: Parent
    ROLE: Uses
  - TYPE: Parent
    ROLE: ConformsTo
